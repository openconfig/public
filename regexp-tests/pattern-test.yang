module pattern-test {
  prefix "pt";
  namespace "urn:openconfig-pattern-test";

  description
    "contains extensions for executing pattern tests as well as plugin test
    cases";

  extension pattern-test-pass {
    argument "testcase" {
      yin-element false;
    }
    description
      "A matching pattern for the given leaf.";
  }

  extension pattern-test-fail {
    argument "testcase" {
      yin-element false;
    }
    description
      "A non-matching pattern for the given leaf.";
  }
}
