module openconfig-isis-types-test {
  prefix "rt";
  namespace "urn:openconfig-isis-types-test";

  import pattern-test { prefix "pt"; }
  import openconfig-isis-types { prefix "ocist"; }

  leaf isis-net {
    type ocist:net;
    pt:pattern-test-pass "49.1270.0000.0001.00";
    pt:pattern-test-pass "49.0001.1270.0000.0001.00";
    pt:pattern-test-pass "49.0001.AE12.DEAD.BEEF.0000.0000.0000.0000.0000.9A";
    pt:pattern-test-fail "490.0001.1270.0000.0001.00";
    pt:pattern-test-fail "49.0001.1270.0.0001.1";
    pt:pattern-test-fail "49.0001.1270.00";
    pt:pattern-test-fail "49.0001.1270.0000.000X.00";
  }

  leaf isis-area-address {
    type ocist:area-address;
    pt:pattern-test-pass "49";
    pt:pattern-test-pass "49.0001";
    pt:pattern-test-pass "49.ABCD.abcd.Ef09";
    pt:pattern-test-fail "49.0001.";
    pt:pattern-test-fail "49.0001.0002.0003.0004";
  }

  leaf isis-system-id {
    type ocist:system-id;
    pt:pattern-test-pass "0123.4567.89aB";
    pt:pattern-test-pass "ABCD.abcd.efEF";
    pt:pattern-test-fail "ABCD.abcd.efgG";
    pt:pattern-test-fail "0001.0002.0003.0004";
    pt:pattern-test-fail "0001.0002";
  }

  leaf isis-lsp-id {
    type ocist:lsp-id;
    pt:pattern-test-pass "0123.4567.89aB.00-00";
    pt:pattern-test-pass "ABCD.abcd.efEF.67-89";
    pt:pattern-test-fail "ABCD.abcd.efEF";
    pt:pattern-test-fail "0001.0002.0003.ae-1f";
    pt:pattern-test-fail "0001.0002.00-00";
  }
}
