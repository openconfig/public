module openconfig-bgp-policy-test {
  prefix "oc-bgp-pol-t";
  namespace "urn:openconfig-bgp-policy-test";

  import pattern-test { prefix "pt"; }
  import openconfig-bgp-policy { prefix "oc-bgp-pol"; }

  leaf set-med {
    type oc-bgp-pol:bgp-set-med-type;
    // Increment/Decrement notation
    pt:pattern-test-pass "+3";
    pt:pattern-test-pass "-33";
    pt:pattern-test-pass "+100";
    pt:pattern-test-pass "-100";
    pt:pattern-test-pass "+11100";
    pt:pattern-test-pass "-11100";
    pt:pattern-test-pass "+9999999999";
    pt:pattern-test-pass "-9999999999";
    pt:pattern-test-fail "+A01";
    pt:pattern-test-fail "-A01";
    pt:pattern-test-fail "?1000";
  }
}
