module openconfig-aft-counters {
  namespace "http://openconfig.net/yang/aft-counters";
  prefix "oc-aft-counters";

  import openconfig-extensions { prefix "oc-ext"; }
  import openconfig-inet-types { prefix "oc-inet"; }
  import openconfig-mpls-types { prefix "oc-mplst"; }
  import openconfig-network-instance { prefix "oc-ni"; }
  import openconfig-yang-types { prefix "oc-yang"; }

  organization
    "OpenConfig working group";

  contact
    "OpenConfig working group
    www.openconfig.net";

  description
    "Submodule providing a unified subtree for AFT entry counters.";

  oc-ext:openconfig-version "3.4.0";

  revision "2026-05-20" {
    description
      "Add IPv4, IPv6, and MPLS multicast AFT counter containers, and a
       new aft-multicast-entry-counter-state grouping for multicast-only
       counters (rpf-discards).";
    reference "3.4.0";
  }

  revision "2026-02-09" {
    description
      "Deprecate popped-mpls-label-stack and AFT NH pushed-mpls-label-stack
       and mpls-label-stack leafs as they do not support duplicates.
       Add decap-mpls-label-stack and AFT NH encap-mpls-label-stack
       and encap-mpls-label-stack leafs that support duplicates.";
    reference "3.3.0";
  }

  revision "2025-07-04" {
    description
      "Factor out AFT counters from atomic container into a unified subtree.";
    reference "3.2.0";
  }

  grouping aft-entry-counter-state {
    description
      "Counters relating to a forwarding entry";

    leaf packets-forwarded {
      type oc-yang:counter64;
      description
        "The number of packets which have matched, and been forwarded,
        based on the AFT entry.";
    }

    leaf octets-forwarded {
      type oc-yang:counter64;
      description
        "The number of octets which have matched, and been forwarded,
        based on the AFT entry";
    }
  }

  grouping aft-backup-entry-counter-state {
    description
      "Counters relating to a backup forwarding entry";

    leaf packets-forwarded-backup {
      type oc-yang:counter64;
      description
        "The number of packets which have matched, and been forwarded,
        based on the AFT backup entry.";
    }

    leaf octets-forwarded-backup {
      type oc-yang:counter64;
      description
        "The number of octets which have matched, and been forwarded,
        based on the AFT backup entry";
    }
  }

  grouping aft-multicast-entry-counter-state {
    description
      "Counters specific to multicast forwarding entries.";

    leaf rpf-discards {
      type oc-yang:counter64;
      description
        "The number of packets discarded because the arrival interface
        did not match the reverse-path interface programmed for this
        multicast entry.";
    }
  }

  grouping aft-counters-top {
    description
      "Unified subtree for AFT entry counters, organized by protocol and entry.";

    container counters {
      config false;
      description
        "Unified subtree for AFT entry counters, organized by protocol and entry.";

      container ipv4-unicast {
        description
          "Counters for IPv4 unicast AFT entries.";

        list ipv4-entry {
          key "prefix";
          description
            "Counters for each IPv4 unicast AFT entry, keyed by prefix.";

          leaf prefix {
            type leafref {
              path "../state/prefix";
            }
            description
              "Reference to the destination prefix which
              must be matched to utilize the AFT entry.";
          }

          container state {
            config false;
            description
              "Counter state for the IPv4 unicast AFT entry.";

            leaf prefix {
              type oc-inet:ipv4-prefix;
              description
                "The IPv4 destination prefix that should be matched to
                utilize the AFT entry.";
            }

            uses aft-entry-counter-state;
            uses aft-backup-entry-counter-state;
          }
        }
      }

      container ipv6-unicast {
        description
          "Counters for IPv6 unicast AFT entries.";

        list ipv6-entry {
          key "prefix";
          description
            "Counters for each IPv6 unicast AFT entry, keyed by prefix.";

          leaf prefix {
            type leafref {
              path "../state/prefix";
            }
            description
              "Reference to the destination prefix which
              must be matched to utilize the AFT entry.";
          }

          container state {
            config false;
            description
              "Counter state for the IPv6 unicast AFT entry.";

            leaf prefix {
              type oc-inet:ipv6-prefix;
              description
                "The IPv6 destination prefix that should be matched to
                utilize the AFT entry.";
            }

            uses aft-entry-counter-state;
            uses aft-backup-entry-counter-state;
          }
        }
      }

      container mpls {
        description
          "Counters for MPLS AFT entries.";

        list label-entry {
          key "label";
          description
            "Counters for each MPLS AFT entry, keyed by label.";

          leaf label {
            type leafref {
              path "../state/label";
            }
            description
              "Reference to the label which must be matched to
              utilize the AFT entry.";
          }

          container state {
            config false;
            description
              "Counter state for the MPLS AFT entry.";

            leaf label {
              type oc-mplst:mpls-label;
              description
                "The MPLS label that should be matched to utilize the AFT entry.";
            }

            uses aft-entry-counter-state;
          }
        }
      }

      container ipv4-multicast {
        description
          "Counters for IPv4 multicast AFT entries.";

        list ipv4-multicast-entry {
          key "source-address group-address";
          description
            "Counters for each IPv4 multicast AFT entry, keyed by the
            (source, group) pair.";

          leaf source-address {
            type leafref {
              path "../state/source-address";
            }
            description
              "Reference to the IPv4 source address.";
          }

          leaf group-address {
            type leafref {
              path "../state/group-address";
            }
            description
              "Reference to the IPv4 multicast group address.";
          }

          container state {
            config false;
            description
              "Counter state for the IPv4 multicast AFT entry.";

            leaf source-address {
              type oc-inet:ipv4-address;
              description
                "The IPv4 source address for this multicast entry. The
                value 0.0.0.0 represents any-source (*,G) entries.";
            }

            leaf group-address {
              type oc-inet:ipv4-address;
              description
                "The IPv4 multicast group address for this entry.";
            }

            uses aft-entry-counter-state;
            uses aft-multicast-entry-counter-state;
          }
        }
      }

      container ipv6-multicast {
        description
          "Counters for IPv6 multicast AFT entries.";

        list ipv6-multicast-entry {
          key "source-address group-address";
          description
            "Counters for each IPv6 multicast AFT entry, keyed by the
            (source, group) pair.";

          leaf source-address {
            type leafref {
              path "../state/source-address";
            }
            description
              "Reference to the IPv6 source address.";
          }

          leaf group-address {
            type leafref {
              path "../state/group-address";
            }
            description
              "Reference to the IPv6 multicast group address.";
          }

          container state {
            config false;
            description
              "Counter state for the IPv6 multicast AFT entry.";

            leaf source-address {
              type oc-inet:ipv6-address;
              description
                "The IPv6 source address for this multicast entry. The
                value :: represents any-source (*,G) entries.";
            }

            leaf group-address {
              type oc-inet:ipv6-address;
              description
                "The IPv6 multicast group address for this entry.";
            }

            uses aft-entry-counter-state;
            uses aft-multicast-entry-counter-state;
          }
        }
      }

      container mpls-multicast {
        description
          "Counters for MPLS multicast (P2MP) AFT entries.";

        list multicast-label-entry {
          key "label";
          description
            "Counters for each MPLS multicast AFT entry, keyed by the
            incoming label.";

          leaf label {
            type leafref {
              path "../state/label";
            }
            description
              "Reference to the MPLS label.";
          }

          container state {
            config false;
            description
              "Counter state for the MPLS multicast AFT entry.";

            leaf label {
              type oc-mplst:mpls-label;
              description
                "The MPLS label that should be matched to utilize the
                AFT entry.";
            }

            uses aft-entry-counter-state;
          }
        }
      }

      container ethernet {
        description
          "Counters for Ethernet AFT entries.";

        list mac-entry {
          key "mac-address";
          description
            "Counters for each Ethernet AFT entry, keyed by MAC address.";

          leaf mac-address {
            type leafref {
              path "../state/mac-address";
            }
            description
              "Reference to the mac-address that should be matched to utilize the
              AFT entry.";
          }

          container state {
            config false;
            description
              "Counter state for the Ethernet AFT entry.";

            leaf mac-address {
              type oc-yang:mac-address;
              description
                "The MAC address that should be matched to utilize the AFT entry.";
            }

            uses aft-entry-counter-state;
          }
        }
      }

      container policy-forwarding {
        description
          "Counters for Policy Forwarding AFT entries.";

        list policy-forwarding-entry {
          key "index";
          description
            "Counters for each Policy Forwarding AFT entry, keyed by index.";

          leaf index {
            type leafref {
              path "../state/index";
            }
            description
              "Reference to the index that should be matched to utilize the
              AFT entry.";
          }

          container state {
            config false;
            description
              "Counter state for the Policy Forwarding AFT entry.";

            leaf index {
              type uint64;
              description
                "The index that should be matched to utilize the Policy Forwarding AFT entry.";
            }

            uses aft-entry-counter-state;
          }
        }
      }

      container next-hops {
        description
          "Counters for Next-Hop AFT entries.";

        list next-hop {
          key "index";
          description
            "Counters for each Next-Hop AFT entry, keyed by index.";

          leaf index {
            type leafref {
              path "../state/index";
            }
            description
              "Reference to the index of the next-hop that should be matched to utilize
              the AFT entry.";
          }

          container state {
            config false;
            description
              "Counter state for the Next-Hop AFT entry.";

            leaf index {
              type uint64;
              description
                "The index that should be matched to utilize the Next-Hop AFT entry.";
            }

            uses aft-entry-counter-state;
          }
        }
      }
    }
  }
  augment "/oc-ni:network-instances/oc-ni:network-instance/oc-ni:afts" {
    description
      "Attach counters to AFT tree.";

    uses aft-counters-top;
  }
}
