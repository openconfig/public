submodule openconfig-aft-ipv6-multicast {
  belongs-to "openconfig-aft" {
    prefix "oc-aft";
  }

  import openconfig-extensions { prefix "oc-ext"; }
  import openconfig-inet-types { prefix "oc-inet"; }
  import openconfig-interfaces { prefix "oc-if"; }

  // Include common cross-AFT groupings from the common submodule.
  include openconfig-aft-common;

  organization
    "OpenConfig working group";

  contact
    "OpenConfig working group
    www.openconfig.net";

  description
    "Submodule containing definitions of groupings for the abstract
    forwarding table for IPv6 multicast.";

  oc-ext:openconfig-version "0.1.0";

  revision "2026-05-20" {
    description
      "Initial revision of the IPv6 multicast abstract forwarding table.";
    reference "0.1.0";
  }

  grouping aft-ipv6-multicast-structural {
    description
      "Structural grouping defining the schema for the IPv6 multicast
      abstract forwarding table.";

    list ipv6-multicast-entry {
      key "source-address group-address";

      oc-ext:telemetry-atomic;
      description
        "List of the IPv6 multicast entries within the abstract
        forwarding table. Each entry is keyed by the (source, group)
        pair. The source-address :: represents any-source (*,G)
        entries used for shared-tree and BiDir RP forwarding.";

      leaf source-address {
        type leafref {
          path "../state/source-address";
        }
        description
          "Reference to the IPv6 source address. Use :: for
          any-source (*,G) entries.";
      }

      leaf group-address {
        type leafref {
          path "../state/group-address";
        }
        description
          "Reference to the IPv6 multicast group address.";
      }

      container state {
        config false;
        description
          "Operational state parameters for the IPv6 multicast AFT
          entry.";
        uses aft-ipv6-multicast-entry-state;
      }

    }
  }

  grouping aft-ipv6-multicast-entry-state {
    description
      "Operational state parameters for the IPv6 multicast entry.";

    leaf source-address {
      type oc-inet:ipv6-address;
      description
        "The IPv6 source address for this multicast entry. The value
        :: represents any-source (*,G) entries.";
    }

    leaf group-address {
      type oc-inet:ipv6-address;
      description
        "The IPv6 multicast group address for this entry.";
    }

    uses aft-common-entry-state;
    uses aft-common-ip-state;

    container reverse-path-interface {
      description
        "Reference to the incoming (reverse-path) interface used by
        the forwarding plane to validate the arrival of packets for
        this multicast entry. Packets received on any other interface
        are discarded (see the rpf-discards counter).

        For directly-connected sources, or where the system does not
        program an RPF interface for the entry (e.g. bidirectional
        PIM in some implementations), this container may be absent.";

      uses oc-if:interface-ref-state;
    }
  }
}
