module openconfig-system-gnpsi {
  yang-version "1";

  // namespace
  namespace "http://openconfig.net/yang/system/gnpsi";

  prefix "oc-system-gnpsi";

  // import some basic types
  import openconfig-extensions { prefix oc-ext; }
  import openconfig-inet-types { prefix oc-inet; }
  import openconfig-yang-types { prefix oc-yang; }
  import openconfig-system { prefix oc-sys; }
  import openconfig-system-grpc { prefix oc-sys-grpc; }

  // meta
  organization "OpenConfig working group";

  contact
    "OpenConfig working group
    www.openconfig.net";

  description
    "This module defines configuration and operational state data
    related to gRPC Network Packet Sampling Interface.";

  revision "2024-04-01" {
    description
      "Initial revision";
    reference "1.0.0";
  }

  oc-ext:openconfig-version "1.0.0";


  grouping gnpsi-clients-state {
    description
      "Operational data for gNPSI clients.";

    leaf address {
      type oc-inet:ip-address;
      description
        "IPv4/IPv6 address of the gNPSI client.";
    }

    leaf port {
      type oc-inet:port-number;
      default 6343;
      description
        "UDP port number for the gNPSI client.";
    }

    leaf bytes-sent {
      type oc-yang:counter64;
      description
        "The total number of bytes sampled and sent to the
        client.";
    }

    leaf packets-sent {
      type oc-yang:counter64;
      description
        "The total number of packets sampled and sent to the
        client.";
    }

    leaf packets-error {
      type oc-yang:counter64;
      description
        "The total number of error packets failed to be sampled
        and sent to the client.";
    }
  }

  grouping gnpsi-clients-top {
    description
      "Top-level grouping for data related to gNPSI clients.";

    container clients {
      config false;
      description
        "Enclosing container for list of gNPSI clients.";

      list client {
        key "address port";
        description
          "List of gNPSI clients to send sampling data.  Packet
          samples are sent to all clients specified.";

        leaf address {
          type leafref {
            path "../state/address";
          }
          description
            "Reference to address list key.";
        }

        leaf port {
          type leafref {
            path "../state/port";
          }
          description
            "Reference to port list key.";
        }

        container state {
          config false;
          description
            "Operational state data for gNPSI clients.";

          uses gnpsi-clients-state;
        }
      }
    }
  }

  augment "/oc-sys:system/oc-sys-grpc:grpc-servers/oc-sys-grpc:grpc-server" {
    description
      "Add gNPSI configuration/state to the openconfig-sampling model.";

    uses gnpsi-clients-top;
  }
}
