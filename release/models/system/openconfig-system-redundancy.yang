module openconfig-system-redundancy {

  yang-version "1";

  // namespace
  namespace "http://openconfig.net/yang/system/redundancy";

  prefix "oc-sys-red";

  // import some basic types
  import openconfig-extensions { prefix oc-ext; }
  import openconfig-system { prefix oc-sys; }
  import openconfig-types { prefix oc-types; }
  import openconfig-inet-types { prefix oc-inet; }
  import openconfig-interfaces { prefix oc-if; }
  import openconfig-platform { prefix oc-platform; }

  // meta
  organization "OpenConfig working group";

  contact
    "OpenConfig working group
    www.openconfig.net";

  description
    "This module defines the configuration and operational state data
    related to redundant systems, such as two supervisors in a device.";

  oc-ext:openconfig-version "0.1.0";

  revision "2023-01-06" {
    description
      "Initial revision with management-active redundancy";
    reference "0.1.0";
  }

  // extension statements

  // feature statements

  // identity statements
  identity SYSTEM_MANAGEMENT_REDUNDANCY_MODE_BASE {
    description
      "Base identity for redundancy modes for management-active interface.";
  }

  identity SYSTEM_MANAGEMENT_REDUNDANCY_DISABLED {
    base SYSTEM_MANAGEMENT_REDUNDANCY_MODE_BASE;
    description
      "Disable redundancy for management-active interface.";
  }

  identity SYSTEM_MANAGEMENT_REDUNDANCY_MONITOR_LINK_STATE {
    base SYSTEM_MANAGEMENT_REDUNDANCY_MODE_BASE;
    description
      "Enable redundancy for management-active interface with 
      link-state monitor for redundant management links.";
  }

  identity SYSTEM_MANAGEMENT_REDUNDANCY_MONITOR_NEIGHBOR {
    base SYSTEM_MANAGEMENT_REDUNDANCY_MODE_BASE;
    description
      "Enable redundancy for management-active interface with
      nieghbor reachability monitor via redundant management links.";
  }

  // typedef statements
  typedef fallback-delay-value-seconds16 {
    type union {
      type uint16 {
        range "0..3600";
      }
      type enumeration {
        enum INFINITY {
          description
            "The delay is set to infinity.";
        }
      }
    }
    units "seconds";
    description
      "Fallback delay value type, in seconds (16-bit range).";
  }

  // grouping statements
  grouping management-active-controller-card-config {
    description
      "Configuration data for controller card components.";

    leaf name {
      type leafref {
        path "/oc-platform:components/oc-platform:component/oc-platform:name";
      }
      description
        "References the controller card component.";
    }

    leaf-list interface {
      type leafref {
        path "/oc-if:interfaces/oc-if:interface/oc-if:name";
      }
      ordered-by user;

      description
        "Ordered list of redundant management links for
        managment-active interface when this controller
        card is active.";
    }
  }

  grouping management-active-controller-card-state {
    description
      "Operational state data for controller card components.";
  }

  grouping management-active-controller-card-list {
    description
      "Top-level grouping for list of controller card components.";

    container controller-cards {
      description
        "Top-level container for list of controller card components.";

      list controller-card {
        key "name";
        description
          "Controller card name";

        leaf name {
          type leafref {
            path "../config/name";
          }

          description
            "References the controller card name";
        }

        container config {
          description
            "Configuration data for controller card components.";
          uses management-active-controller-card-config;
        }

        container state {
          config false;
          description
            "Operational state data for controller card components.";
          uses management-active-controller-card-config;
          uses management-active-controller-card-state;
        }
      }
    }
  }

  grouping management-active-current-active-config {
    description
      "Configuration data for management-active interface current active.";
  }

  grouping management-active-current-active-state {
    description
      "Operational state data for management-active interface current active.";

    leaf active-controller-card {
      type leafref {
        path "../../controller-cards/controller-card/name";
      }

      description
        "References the active controller card component";
    }

    leaf active-interface {
      type leafref {
        path "/oc-if:interfaces/oc-if:interface/oc-if:name";
      }

      description
        "References the active management link";
    }
  }

  grouping management-active-redundant-link-top {
    description
      "Top-level grouping for management-active interface redundant links.";

    container redundant-link {
      description
        "Top-level container for management-active interface redundant links.";

      container config {
        description
          "Configuration data for management-active interface current active.";
        uses management-active-current-active-config;

      }

      container state {
        config false;
        description
          "Operational state data for management-active interface current active.";

        uses management-active-current-active-config;
        uses management-active-current-active-state;
      }

      uses management-active-controller-card-list;
    }
  }

  grouping management-active-neighbor-monitor-config {
    description
      "Configuration data for neighbor monitor.";

    leaf neighbor-monitor {
      type oc-inet:ip-address;
      description
        "Neighbor address to be monitored.";
    }

    leaf monitor-interval {
      type uint32 {
        range "1..300000";
      }
      units "milliseconds";      
      default 200;
      description
        "Interval for sending ARP or NS request packets to the neighbor.";
    }

    leaf timeout-multiplier {
      type uint8 {
        range 1..100;
      }
      default 3;
      description
        "Maximum number of missed ARP or NA replies from the neighbor after
        which the failover occurs.";
    }
  }

  grouping management-active-neighbor-monitor-state {
    description
      "Operational state data for neighbor monitor.";
  }

  grouping management-active-neighbor-monitor-top {
    description
      "Top-level grouping for neighbor monitor data.";

    container neighbor-monitor {
      description
        "Top-level container for neighbor monitor data.";

      container config {
        description
          "Configuration data for neighbor monitor.";

        uses management-active-neighbor-monitor-config;
      }

      container state {
        config false;
        description
          "Operational state data for neighbor monitor.";

        uses management-active-neighbor-monitor-config;
        uses management-active-neighbor-monitor-state;
      }
    }
  }

  grouping redundancy-management-active-config {
    description
      "Configuration data for management-active interface redundancy.";

    leaf redundancy-mode {
      type identityref {
        base SYSTEM_MANAGEMENT_REDUNDANCY_MODE_BASE;
      }
      default SYSTEM_MANAGEMENT_REDUNDANCY_DISABLED;
      description
        "Redundancy mode for management-active interface.";
    }

    leaf fallback-delay {
      type fallback-delay-value-seconds16;
      default INFINITY;
      description
        "Delay after which a higher priority management link
        will be considered to fallback after it has come up.
        If set to infinity, then dont automatically fallback.";
    }
  }

  grouping redundancy-management-active-state {
    description
      "Operational state data for management-active interface redundancy.";

    leaf last-redundancy-config-change {
      type oc-types:timeticks64;
      units "nanoseconds";

      description
        "This timestamp indicates the time redundancy configuration
        was last applied to management-active interface.
        The value is the timestamp in nanoseconds relative
        to the Unix Epoch (Jan 1, 1970 00:00:00 UTC).";
    }

    leaf last-redundancy-link-change {
      type oc-types:timeticks64;
      units "nanoseconds";

      description
        "This timestamp indicates the time active link was
        last changed for management-active interface.
        The value is the timestamp in nanoseconds relative
        to the Unix Epoch (Jan 1, 1970 00:00:00 UTC).";
    }
  }

  grouping redundancy-management-active-top {
    description
      "Top-level grouping for management-active interface redundancy data.";

    container management-active {
      description
        "Top-level container for management-active interface redundancy
        data. The management-active is a logical interface on
        modular systems providing out of band access to the active
        controller card";

      container config {
        description
          "Configuration data for management-active interface redundancy.";

        uses redundancy-management-active-config;
      }

      container state {
        config false;
        description
          "Operational state data for management-active interface redundancy.";

        uses redundancy-management-active-config;
        uses redundancy-management-active-state;
      }

      uses management-active-neighbor-monitor-top;
      uses management-active-redundant-link-top;
    }
  }

  grouping system-redundancy-top {
    description
      "Top-level grouping for system level redundancy features.";

    container redundancy {
      description
        "Top-level container for system level redundancy features.";

      uses redundancy-management-active-top;
    }
  }

  // data definition statements

  // augment statements
  augment "/oc-sys:system" {
    description
      "Add redundancy features to the openconfig-system model.";

    uses system-redundancy-top;
  }

  // rpc statements

  // notification statements
}
