module openconfig-system-controlplane {
    yang-version "1";

    namespace "http://openconfig.net/yang/system-controlplane";
    prefix "oc-sys-copp";

    import openconfig-extensions {
        prefix oc-ext;
    }
    import openconfig-system {
        prefix oc-sys;
    }
    import openconfig-acl {
        prefix oc-acl;
    }
    import openconfig-qos {
        prefix oc-qos;
    }

    organization
      "OpenConfig working group";
    contact
      "www.openconfig.net";

    description
      "This module adds configuration and operational state relating to
       policies for traffic destined to the system's control-plane.
       Particularly, it allows for mechanisms to:
        - apply an ACL that forwards or drops traffic towards the control-plane.
        - classify traffic that is destined to the control-plane according to
          a QoS classifier.
        - schedule traffic that has been forwarded towards the control-plane,
          to allow for policies such as rate limits to be applied.
       The configured policies apply generically to all control-planes that
       exist within the system, and should be mapped to the internal interfaces
       via which packets are forwarded to control-plane modules.
       When a packet is received at an input interface - it is classified into a
       forwarding group which drains to a specific queue. If this input mapping
       is sufficient, the CPU-facing interface uses the specified scheduler
       to determine how to drain queues. If more granular remapping is required
       (e.g., to classify control-plane traffic more granularly), a user specifies
       an alternate classifier that is used to reclassify traffic into
       a new set of forwarding-groups (and hence queues) that can subsequently
       be scheduled by the specified scheduler.
       The specified control-plane ACL is applied to traffic received by the
       control-plane of the system.";

    oc-ext:openconfig-version "0.3.0";
    oc-ext:catalog-organization "openconfig";
    oc-ext:origin "openconfig";

    revision "2023-10-16" {
      description
        "Add embedded-limits container for  vendor-neutral, abstract expression
        of platform built-in protection limits";
      reference "0.3.0";
    }

    revision "2023-03-03" {
      description
        "Add missing state container to ACL.";
      reference "0.2.0";
    }

    revision "2021-08-02" {
      description
        "Initial revision.";
      reference "0.1.0";
    }

    grouping system-controlplane-top {
      description
        "Top-level structural grouping for control-plane traffic policies.";

      container control-plane-traffic {
        description
          "Policies and configuration relating to the traffic destined towards
            the system control-plane.";

        container ingress {
          description
            "Control-plane traffic parameters relating to ingress traffic.
            This refers to traffic that is being received by the system's
            control plane from external-to-the-controlplane sources.";

          uses system-controlplane-acl-common-top;

          container qos {
            description
              "Configuration and operational state relating to QoS policies
              that are applied to control-plane traffic.";

            container scheduler-policy {
              description
                "Configuration and operational state relating to the QoS
                scheduler policy that is applied to control-plane traffic.
                The scheduler policy determines how traffic, classified by
                the specified control-plane classifier is rate-limited towards
                the control-plane. The scheduler policy is defined in
                /qos/scheduler-policies.";

              container config {
                description
                  "Configuration parameters relating to the scheduler-policy
                  that is to be applied control-plane traffic.";

                uses system-controlplane-qos-scheduler-config;
              }

              container state {
                config false;
                description
                  "Operational state parameters relating to the scheduler policy
                  applied to the control-plane traffic.";

                uses system-controlplane-qos-scheduler-config;
              }

              container scheduler-statistics {
                config false;
                description
                  "Operational state and counters relating to the
                  scheduler-policy applied to control plane traffic.";

                list scheduler {
                  key "sequence";
                  description
                    "List of the schedulers that are part of the scheduler-policy
                    specified.";

                  leaf sequence {
                    type leafref {
                      path "../state/sequence";
                    }
                    description
                      "Reference to the sequence ID for the scheduler.";
                  }

                  container state {
                    description
                      "Operational state parameters relating to the scheduler
                      policy.";

                    uses system-controlplane-qos-scheduler-seq-state;
                  }
                }
              }
            }
          }
          container built-in-limits {
            description
              "Each platform  and vendor has some implementation of
              built-in protection of control-plane, that is software running on
              general purpose CPU, against excessive ingress rate of incomming
              traffic.
              These implementations may vary significantly among vendors and
              platforms.
              This container provides a vendor-neutral, abstract, aggregated,
              system-level view into packets delivered to the control-plane for
              processing as well as packets dropped due to embedded control plane
              protection rules.
              Furthermore, this container provides an anchor point for vendor
              extension to provide more detailed platform
              specific view and ability to modify some attributes of built-in
              control plane protection rules (e.g. packet rate limits and burst
              sizes).
              ";
            container state {
              description
                "Vendor-neutral, abstract and aggregated system-level counters for
                 packets sent to the control-plane which may be dropped or accepted
                 for processing as defined by built-in control plane traffic limiting rules.";
              config false;
              container counters {
                description
                  "Packet, octets counters for uilt-in limits";
                container bgp-aggregate {
                  description
                    "BGP protocol packets with destination of this device.";
                  uses system-controlplane-built-in-limits-traffic-state;
                }
                container rsvp-aggregate {
                  description
                    "RSVP protocol packets passing this device";
                  uses system-controlplane-built-in-limits-traffic-state;
                }
                container l3-routing-aggregate {
                  description
                    "Traffic with destination of this device, of all L3 routing
                    protocols except bgp and rsvp, which have their own counters,
                    for example: ISIS, OSPF, LDP, PIM, etc.";

                  uses system-controlplane-built-in-limits-traffic-state;
                }
                container l3-control-aggregate {
                  description
                    "Layer 3 control plane traffic with destination of this device which
                    are not routing protocols and do not have an explicit container
                    already identified.  For example: ICMP, VRRP, IPv6 ND, BFD,
                    MPLS-OAM, IGMP, etc";
                  uses system-controlplane-built-in-limits-traffic-state;
                }
                container l2-control-aggregate {
                  description
                    "Layer 2 control traffic with destination of this device, for
                    example: ARP, LACP, LLDP, Eth-OAM, BPDU, etc.";
                  uses system-controlplane-built-in-limits-traffic-state;
                }
                container trap-exeption-aggregate {
                  description
                    "Traffic with destination other than the given device which are not
                    forwarded but punted to the device control plane for processing.
                    Examples are: TTL=1, egress MTU exceeded and DF set, no next-hop
                    L2 address known - ARP/ND triggering, no match in FIB - ICMP no
                    route to destination generation, etc";
                  uses system-controlplane-built-in-limits-traffic-state;
                }
                container sample-redirect-aggregate {
                  description
                    "Packets with destination other than the given device which are
                    punted to the control plane via user provided policy (e.g. P4RT)
                    or configuration such as packet mirroring or packet sampling.
                    For example, port mirroring, sFlow, IPFIX, etc.";
                  uses system-controlplane-built-in-limits-traffic-state;
                }
                container management-aggregate {
                  description
                    "Traffic targeted this device used management - ssh,
                    telnet, ftp, gN*, snmp, netconf, rest, etc";
                  uses system-controlplane-built-in-limits-traffic-state;
                }
                container remaining-aggregate {
                  description "all other packets send to control plane";
                  uses system-controlplane-built-in-limits-traffic-state;
                }
              }
            }
            container vendor {
              description
                "An anchor point for vendor and platform specific
                extensions.
                As each platform  and vendor has different implementation and internal
                parts where packets may be dropped at any point in time. Providing
                vendor-specific counters provides better visibility into control-plane
                traffic.
                The recommended usage of this container is to create an augment at
                /system/control-plane-traffic/ingress/built-in-limits/vendor that contains additional
                vendor/platform specific containers.
                e.g.
                augment /system/control-plane-traffice/ingress/built-in-limits/vendor {
                  container <vendor name> {
                    container <platform name> {
                      container <traffic-group-name>
                        container config {
                          leaf packet-max-rate {
                            type int64;
                            description \"Packet rate in packets-per-second\";
                              ...
                            }
                          leaf packet-burst-size {
                            type int64;
                            description \"Burst size in Bytes\";
                              ...
                          }
                          ...
                          }
                          container state {
                            leaf packet-max-rate {
                              type int64;
                              description \"Packet rate in packets-per-second\";
                              ...
                            }
                            leaf packet-burst-size {
                              type int64;
                              description \"Burst size in Bytes\";
                              ...
                            }
                            ...
                            leaf aggregate-counter-name {
                              type leaf-ref;
                              description
                                \"One of built-in counters defined under ../built-in-limits/state/counters/,
                                such 'bgp-aggregate' or 'l2-control-aggregate'.
                                This self-documentation allows client to asssociate multiple vendor
                                counters with vendor-neutral, abstract, aggregated counters.\";
                            }
                            container counters {
                              description \"Counters of packets and octets for given traffic-group-name\";
                              uses system-controlplane-built-in-limits-traffic-state;
                            }
                          }
                        }
                      }
                    }
                  }

                In addition to above, more granular packet/octet counters, also information
                about rate limit and allowd burst size for each counter should be exposed.
                Furthermore ability to configure rate limit and allowd burst size for each
                counter could be exposed.
                When vendor extension exists it MUST provide aggregate-counter-name leaf,
                and must provide counters for accepted and discarded packets and octets for
                each <traffic-group-name>";
            }
          }
        }

        container egress {
          description
            "Control-plane traffic parameters relating to egress traffic.
            This refers to traffic that is sent by the system's control
            plane to external-to-the-controlplane destinations.";

          uses system-controlplane-acl-common-top;
        }
      }
    }

    grouping system-controlplane-acl-common-top {
      description
        "Common structural grouping for ACL configuration and state for
        control plane traffic.";

      container acl {
        description
          "Configuration and operational state parameters relating to the
          access control list applied to control-plane traffic.";

        list acl-set {
          key "set-name type";

          description
            "List of the ACL that is to be applied in the specific ingress
            or egress context. The key of the list specifies the type of
            traffic to be matched, along with a reference to an ACL
            configured in the OpenConfig ACL model within the /acl hierarchy.";

          leaf set-name {
            type leafref {
              path "../config/set-name";
            }
            description
              "Reference to the name of the ACL-set to be applied.";
          }

          leaf type {
            type leafref {
              path "../config/type";
            }
            description
              "Reference to the type of the ACL-set to be applied.";
          }

          container config {
            description
              "Configuration parameters relating to the ACL to be applied.";

            uses system-controlplane-common-acl-config;
          }

          container state {
            config false;
            description
              "Operational state parameters relating to the ACL to be applied.";
            uses system-controlplane-common-acl-config;
          }

          uses oc-acl:interface-acl-entries-top;
        }
      }
    }

    grouping system-controlplane-common-acl-config {
      description
        "Grouping for ACL parameters relating to the system control-plane.";

      leaf set-name {
        type leafref {
            path "/oc-acl:acl/oc-acl:acl-sets/oc-acl:acl-set/" +
                  "oc-acl:config/oc-acl:name";
        }
        description
          "Reference to the ACL to be applied to traffic
          in the specified context (ingress or egress).";
      }

      leaf type {
        type leafref {
          path "/oc-acl:acl/oc-acl:acl-sets/oc-acl:acl-set" +
              "[oc-acl:name=current()/../set-name]" +
              "/oc-acl:config/oc-acl:type";
        }
        description
          "Reference to the ACL set type applied to traffic
          in the specified context (ingress or egress).";
      }
    }

    grouping system-controlplane-qos-classifier-config {
      description
        "Grouping for configuration parameters relating to QoS classifiers
        for the system control-plane.";

      leaf name {
          type leafref {
              path "/oc-qos:qos/oc-qos:classifiers/oc-qos:classifier/" +
              "oc-qos:config/oc-qos:name";
          }
          description
            "Reference to a classifier that is used to classify traffic
              destined to the control-plane of the system.
              This classifier determines how packets that match each terms
              are classified into forwarding groups, and subsequently into
              queues to be forwarded.";
      }
    }

    grouping system-controlplane-qos-classifier-term-state {
      description
        "Grouping for control-plane traffic specific leaves required for
        each configuration term.";

      leaf id {
        // Current location /system/control-plane/ingress/qos/classifier/
        // terms/term/state/id
        type leafref {
          path "/oc-qos:qos/oc-qos:classifiers/" +
              "oc-qos:classifier[oc-qos:name=current()/../../../../config/name]" +
              "/oc-qos:terms/oc-qos:term/oc-qos:config/oc-qos:id";
        }
        description
          "Reference to a term identifier within the configured control-plane
          classifier.";
      }
    }

    grouping system-controlplane-qos-scheduler-config {
      description
        "Grouping for configuration parameters relating to the QoS scheduler
        policy for control-plane traffic.";

      leaf name {
          type leafref {
              path "/oc-qos:qos/oc-qos:scheduler-policies/oc-qos:scheduler-policy/" +
              "oc-qos:config/oc-qos:name";
          }
          description
            "Reference to a scheduler policy that determines rate limits, or
            shaping of packets towards the control-plane.";
      }
    }

    grouping system-controlplane-qos-scheduler-seq-state {
      description
        "Grouping for operational state parameters relating to indivual
        schedulers within the applied scheduler policy.";

      leaf sequence {
        type leafref {
          path "/oc-qos:qos/oc-qos:scheduler-policies/oc-qos:scheduler-policy" +
             "[oc-qos:name=current()/../../../../config/name]" +
             "/oc-qos:schedulers/oc-qos:scheduler/oc-qos:config/" +
             "oc-qos:sequence";
        }
        description
          "Reference to a scheduler within the configured scheduler policy.";
      }

      uses oc-qos:qos-scheduler-common-state;
    }

    augment "/oc-sys:system" {
        description
          "Add control-plane configuration and state to the system model.";

        uses system-controlplane-top;
    }
    grouping system-controlplane-built-in-limits-traffic-state {
      description "Packets and Bypes counters for accepted and discarded traffic";
      leaf accepted-pkts {
        type int64;
        description "Packet passed to Control Plane for processing";
      }
      leaf accepted-octets {
        type int64;
        description "Bytes passed to Control Plane for processing";
      }
      leaf dropped-pkts {
        type int64;
        description "Packet discarded";
      }
      leaf dropped-octets {
        type int64;
        description "Bytes discarded";
      }
    }
}
