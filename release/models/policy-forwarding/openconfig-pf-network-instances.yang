submodule openconfig-pf-network-instances {
  belongs-to openconfig-policy-forwarding {
    prefix "oc-pf";
  }

  import openconfig-extensions {
    prefix "oc-ext";
  }
  include openconfig-pf-forwarding-policies;

  organization
    "OpenConfig working group";

  contact
    "OpenConfig working group
     www.openconfig.net";

  description
    "This submodule contains groupings to attach
     a policy-forwarding policy to one or more network-instances.

     When attached to a network-instance, the policy-forwarding rules
     should be evaluated against packets in the specified
     network-instances.";

  oc-ext:openconfig-version "0.8.0";

  revision "2024-11-26" {
    description
      "Add network-instance as an attachment point.";
    reference
      "0.8.0";
  }

  grouping pf-network-instances-structural {
    description
      "Structural grouping for network-instances to forwarding policy
       bindings within the policy-forwarding model.";

    container network-instances {
      description
        "Configuration and operational state relating policy
         forwarding on interfaces.";

      list network-instance {
        key "name";

        description
          "Configuration and operationals state relating to the
           relationship between network-instances and policy-based
           forwarding rules.";

        leaf name {
          type leafref {
            path "../config/name";
          }
          description
            "A reference to the name of the network-instance
             being referenced by the policy.";
        }

        container config {
          description
            "Configuration parameters relating to a network-instance to
             policy forwarding rule binding.";

          uses pf-network-instance-config;
        }

        container state {
          config false;
          description
            "Operational state parameters relating to a network-instance to
             policy forwarding rule binding.";

          uses pf-network-instance-config;
        }
      }
    }
  }

  grouping pf-network-instance-config {
    description
      "Configuration parameters relating to an interface to policy
       forwarding rule binding.";

    leaf name {
      type leafref {
        path "/network-instances/network-instance/" +
           "config/name";
//        path "/oc-netinst:network-instances/oc-netinst:network-instance/" +
//           "oc-netinst:config/oc-netinst:name";
      }
      description
        "A unique identifier for the network-instance.";
    }

    leaf apply-forwarding-policy {
      type leafref {
        // We are at /network-instances/network-instance/
        // policy-forwarding/network-instances/network-instance/config/
        // apply-forwarding-policy
        path "../../../../policies/policy/config/policy-id";
      }
      description
        "The policy to be applied on the network-instance. Packets ingress
         on the referenced interface should be compared to the match
         criteria within the specified policy, and in the case that
         these criteria are met, the forwarding actions specified
         applied. These policies should be applied following quality of
         service classification, and ACL actions if such entities are
         referenced by the corresponding interface.";
    }

    leaf apply-vrf-selection-policy {
      type leafref {
        // We are at /network-instances/network-instance/
        // policy-forwarding/network-instances/network-instance/config/
        // apply-vrf-selection-policy
        path "../../../../policies/policy/config/policy-id";
      }
      description
        "Apply the specific VRF selection policy on the network-instance.

         The referenced policy MUST be of the type VRF_SELECTION_POLICY.
         The VRF selection policy may coexist with a policy-forwarding policy.

         The policy specified in this leaf is used to specifically choose the
         L3VRF network instance that is used for specific input criteria of
         packets.";
    }
  }
}
