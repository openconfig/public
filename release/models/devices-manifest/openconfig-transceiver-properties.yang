module openconfig-transceiver-properties {

  // Yang version can be "1" without mandatory fields.
  // Yang version 1.1 allows mandatory fiels in an augment
  // https://tools.ietf.org/html/rfc7950#section-7.17
  // If the augmentation adds mandatory nodes (see Section 3) that
  // represent configuration to a target node in another module, the
  // augmentation MUST be made conditional with a "when" statement.

  yang-version "1";

  // namespace
  namespace "http://example.net/yang/openconfig-transceiver-properties";

  prefix "oc-trans-properties";

  import openconfig-extensions { prefix oc-ext; }
  import openconfig-alarm-types { prefix oc-alarm-types; }

  // meta
  organization "OpenConfig working group";

  contact
    "OpenConfig working group
      www.openconfig.net";

  description
      "Module to extend OpenConfig transceiver's data to add
      default parameter values which are read from the module.
      These include threshold data for parameters such as input
      power, output power, and laser temperature.";

  oc-ext:openconfig-version "0.1.0";

  // Revisions
  revision "2023-01-12" {
    description
      "Initial implementation of transciever read only parameters
      for laser temperature, input power, and output power.";
    reference "0.1.0";
  }

  // grouping statements
  grouping transceiver-threshold-top {
    description
      "Top-level grouping for transceiver alarm thresholds for
      various sensors.";

    container thresholds {
      description
        "Enclosing container for transceiver alarm thresholds.";

      list threshold {
        config false;
        key "severity";
        description
          "List of transceiver alarm thresholds, indexed by
          alarm severity.";

        leaf severity {
          config false;
          type leafref {
            path "../state/severity";
          }
          description
           "The severity applied to the group of thresholds.
            An implementation's highest severity threshold
            should be mapped to OpenConfig's `CRITICAL`
            severity level.";
        }

        container state {
          config false;
          description
            "Operational alarm thresholds for the transceiver.";

          uses transceiver-threshold-state;
        }
      }
    }
  }

  grouping transceiver-threshold-state {
    description
      "Grouping for all alarm threshold configs for a particular
      severity level.";
    leaf severity {
      type identityref {
        base oc-alarm-types:OPENCONFIG_ALARM_SEVERITY;
      }
      description
        "The type of alarm to which the thresholds apply.";
    }
    leaf laser-temperature-upper {
      description
        "The upper temperature threshold for the laser temperature sensor.";
      type decimal64 {
        fraction-digits 1;
      }
      units celsius;
    }
    leaf laser-temperature-lower {
      description
        "The lower temperature threshold for the laser temperature sensor.";
      type decimal64 {
        fraction-digits 1;
      }
      units celsius;
    }
    leaf output-power-upper{
      description
        "The upper power threshold for the laser output power.";
      type decimal64 {
        fraction-digits 2;
      }
      units dBm;
    }
    leaf output-power-lower{
      description
        "The lower power threshold for the laser output power.";
      type decimal64 {
        fraction-digits 2;
      }
      units dBm;
    }
    leaf input-power-upper{
      description
        "The upper power threshold for the laser input power.";
      type decimal64 {
        fraction-digits 2;
      }
      units dBm;
    }
    leaf input-power-lower{
      description
        "The lower power threshold for the laser input power.";
      type decimal64 {
        fraction-digits 2;
      }
      units dBm;
    }
  }
}
