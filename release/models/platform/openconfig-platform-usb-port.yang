module openconfig-platform-usb-port {

  yang-version "1";

  // namespace
  namespace "http://openconfig.net/yang/platform/usb-port";

  prefix "oc-usb-port";

  import openconfig-platform { prefix oc-platform; }
  import openconfig-extensions { prefix oc-ext; }


  // meta
  organization "OpenConfig working group";

  contact
    "OpenConfig working group
    www.openconfig.net";

  description
    "This module defines data related to USB port components in the
    OpenConfig platform model.";

  oc-ext:openconfig-version "0.1.0";

  revision "2025-09-03" {
    description
      "Initial revision";
    reference "0.1.0";
  }

  // OpenConfig specific extensions for module metadata.
  oc-ext:regexp-posix;
  oc-ext:catalog-organization "openconfig";
  oc-ext:origin "openconfig";

  // grouping statements

  grouping usb-port-top {
    description
      "Top level grouping for attributes related to USB ports.";

    container usb-port {
      description
        "Parameters related to all USB ports.";

      container config {
        description
          "Configuration data for USB ports.";

        uses usb-port-config;
      }

      container state {
        config false;
        description
          "State data for USB ports.";

        uses usb-port-config;
        uses usb-port-state;
      }
    }
  }

  grouping usb-port-config {
    description
      "Configuration data for USB ports.";

    leaf enabled {
      type boolean;
      description
        "Enables or disables USB port functionality.";
    }
  }

  grouping usb-port-state {
    description
      "State data for USB ports.";
  }

  // data definition statements

  // augment statements

  augment "/oc-platform:components/oc-platform:component" {
    description
      "Configuration data for USB ports.";

    uses usb-port-top;
  }
}
