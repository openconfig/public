module openconfig-platform-storage {

yang-version "1";

// namespace
namespace "http://openconfig.net/yang/platform/storage";

prefix "oc-storage";

import openconfig-platform {
  prefix oc-platform;
}
import openconfig-extensions {
  prefix oc-ext;
}
import openconfig-yang-types {
  prefix oc-yang;
}
import openconfig-types {
  prefix oc-types;
}

// meta
organization
  "OpenConfig working group";

contact
  "OpenConfig working group
   www.openconfig.net";

description
  "This module defines data related to STORAGE components in the
   OpenConfig platform model.

    Portions of this code were derived from the following copyright holders.
    References to each copyright holder are mentioned where related content
    is used.

    NVM Express Base Specification Revision 2.0a
    https://nvmexpress.org/wp-content/uploads/NVMe-NVM-Express-2.0a-2021.07.26-Ratified.pdf
    (c) Copyright 2007 to 2021 NVM Express, Inc. ALL RIGHTS RESERVED.
    This NVM Express Base Specification, revision 2.0a is proprietary to the
    NVM Express, Inc. (also referred to as “Company”) and/or its successors
    and assigns.

    S.M.A.R.T. Attribute: Reallocated Sectors Count | Knowledge Base
    http://kb.acronis.com.";

oc-ext:openconfig-version "0.1.2";

revision "2026-01-06" {
  description
    "Fix typo in description for storage statistics entities.";
  reference
    "0.1.2";
}

revision "2025-10-09" {
  description
    "Generalize storage counters in OpenConfig for broader support.";
  reference
    "0.1.1";
}

revision "2024-08-26" {
  description
    "Initial revision.";
  reference
    "0.1.0";
}

// OpenConfig specific extensions for module metadata.
oc-ext:regexp-posix;
oc-ext:catalog-organization "openconfig";
oc-ext:origin "openconfig";

// identity statements
// typedef statements
// grouping statements
  grouping storage-counters-state {
    description
      "Operational state for storage component statistics. These leaves
      are derived from a list of commonly supported storage counters.
      Note that while common, these attributes may not be supported by
      all storage device vendors and media types.";

    leaf soft-read-error-rate {
      type oc-yang:counter64;
      description
        "Uncorrected read errors reported to the operating system.
        This leaf applies to multiple storage technologies, such as:
          - SMART attribute 201.";
      reference
      "S.M.A.R.T. Attribute: Soft Read Error Rate / Off Track Errors (Maxtor)
      | Knowledge Base. kb.acronis.com.";
    }

    leaf reallocated-sectors {
      type oc-yang:counter64;
      description
        "Count of reallocated sectors. The raw value represents a count of
        the bad sectors that have been found and remapped.
        This leaf applies to multiple storage technologies, such as:
          - SMART attribute 5 on SSDs.";
      reference
        "S.M.A.R.T. Attribute: Reallocated Sectors Count | Knowledge Base -
        kb.acronis.com";
    }

    leaf end-to-end-error {
      type oc-yang:counter64;
      description
        "Count of parity errors which occur in the data path to the media.
        This leaf applies to multiple storage technologies, such as:
          - SMART attribute 184.";
      reference
        "Acronis Drive Monitor: Disk Health Calculation Knowledge Base -
        kb.acronis.com";
    }

    leaf offline-uncorrectable-sectors-count {
      type oc-yang:counter64;
      description
        "The total count of uncorrectable errors when reading/writing a
        sector.
        This leaf applies to multiple storage technologies, such as:
          - SMART attribute 198.";
      reference
        "Acronis Drive Monitor: Disk Health Calculation Knowledge Base -
        kb.acronis.com";
    }

    leaf life-left {
      type oc-types:percentage;
      units "percentage";
      description
        "Indicates the approximate remaining life of the storage device, in terms of
        program/erase cycles, available reserved blocks, or an equivalent
        vendor-specific endurance metric. A normalized value of 100 represents
        a new device, with a threshold value at 10 indicating a need for replacement.
        A value of 0 may indicate that the device is operating in read-only mode
        to allow data recovery.
        This leaf applies to multiple storage technologies, such as:
          - SMART attribute 231 on SSDs
          - JEDEC eMMC EXT_CSD life time estimation fields.";
      reference
        "SMART attribute details:
        https://media.kingston.com/support/downloads/MKP_306_SMART_attribute.pdf
        eMMC lifecycle details:
        https://www.kingston.com/en/blog/embedded-and-industrial/emmc-lifecycle";
    }

    leaf percentage-used {
      type uint8;
      units "percentage";
      description
        "Contains a vendor specific estimate of the percentage of device life
        used based on actual usage and the manufacturer’s prediction of device life.
        A value of 100 indicates that the estimated endurance has been consumed,
        but may not indicate device failure. The value is allowed to exceed 100.
        Percentages greater than 254 shall be represented as 255.
        This leaf applies to multiple storage technologies, such as:
          - NVMe devices using the NVM subsystem life estimate.";
      reference
        "NVM Express Base Specification Revision 2.0a
        https://nvmexpress.org/wp-content/uploads/NVMe-NVM-Express-2.0a-2021.07.26-Ratified.pdf";
    }
  }
  grouping storage-state {
    description
      "Storage component state.  These counters are derived from the
       linux kernel block layer statistics in /sys/block/<dev>/stat.
       Implementations which do not use the linux kernel to access
       storage should provide equivalent counters.";
    reference
      "https://www.kernel.org/doc/Documentation/block/stat.txt";

    container counters {
      description
        "A collection of storage specific statistics entities.";

      uses storage-counters-state;
    }
  }

  // data definition statements
  // augment statements
  augment "/oc-platform:components/oc-platform:component/" +
    "oc-platform:storage/oc-platform:state" {
    description
      "Adding storage data to component model";

    uses storage-state;
  }
}
