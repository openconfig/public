module openconfig-platform-controller-card {

  yang-version "1";

  // namespace
  namespace "http://openconfig.net/yang/platform/controller-card";

  prefix "oc-ctrl-card";

  import openconfig-platform { prefix oc-platform; }
  import openconfig-extensions { prefix oc-ext; }


  // meta
  organization "OpenConfig working group";

  contact
    "OpenConfig working group
    www.openconfig.net";

  description
    "This module defines data related to CONTROLLER_CARD components in
    the openconfig-platform model";

  oc-ext:openconfig-version "0.3.0";

  revision "2026-07-08" {
    description
      "Add read-only power-oper-state leaf to controller-card state.";
    reference "0.3.0";
  }

  revision "2024-04-10" {
    description
      "Added details on power-admin-state leaf";
    reference "0.2.0";
  }

  revision "2022-07-28" {
    description
      "Initial revision";
    reference "0.1.0";
  }

  // OpenConfig specific extensions for module metadata.
  oc-ext:catalog-organization "openconfig";
  oc-ext:origin "openconfig";

  // extension statements

  // feature statements

  // identity statements

  // typedef statements

  // grouping statements

  grouping controller-card-config {
    description
      "Configuration data for controller card components";

    uses oc-platform:component-power-management;
  }

  // data definition statements

  // augment statements

  augment "/oc-platform:components/oc-platform:component/" +
    "oc-platform:controller-card/oc-platform:config" {
    description
      "Configuration data for controller card components.
      A controller-card can be configured for persistent powered-off
      mode using the config/power-admin-state leaf. The reference
      path below defines rules for such a configuration.";

    reference
      "Rules around power-off configuration in controller-cards:
      https://github.com/openconfig/public/blob/master/doc/controller-card_poweroff.md";

    uses controller-card-config;
  }

  augment "/oc-platform:components/oc-platform:component/" +
    "oc-platform:controller-card/oc-platform:state" {
    description
      "Adding controller card data to physical inventory. This subtree
      is only valid when the type of the component is CONTROLLER_CARD.";

    uses controller-card-config;
    uses oc-platform:component-power-management-state;
  }

  // rpc statements

  // notification statements

}
