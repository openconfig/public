module openconfig-platform-utilization {

  yang-version "1";

  namespace "http://openconfig.net/yang/platform/utilization";

  prefix "oc-platform-resource";

  import openconfig-platform { prefix oc-platform; }
  import openconfig-platform-linecard { prefix oc-linecard; }
  import openconfig-extensions { prefix oc-ext; }
  import openconfig-types { prefix oc-types; }

  organization "OpenConfig working group";

  contact
    "OpenConfig working group
    www.openconfig.net";

  description
    "This modules contains configurational and operational data for
    resource utilization of components within the platform module.";

  oc-ext:openconfig-version "0.1.0";

  revision "2023-02-10" {
    description
      "Refactor resource utilization.";
    reference "0.1.0";
  }

  grouping resource-utilization-threshold-common {
    description
      "Common threshold configuration model for resource utilization.";

    leaf used-threshold-upper {
      type oc-types:percentage;
      description
        "The used percentage value (used / (used + free) * 100) that
        when crossed will set used-threshold-upper-exceeded to 'true'.";
    }

    leaf used-threshold-upper-clear {
      type oc-types:percentage;
      description
        "The used percentage value (used / (used + free) * 100) that when
        crossed will set used-threshold-upper-exceeded to 'false'.";
    }
  }

  grouping resource-utilization-config {
    description
      "Configuration data for resource utilization.";

    leaf name {
      type string;
      description
        "Resource name within the component.";
    }

    uses resource-utilization-threshold-common;
  }

  grouping resource-utilization-state {
    description
      "Operational state data for resource utilization.";

    leaf used {
      type uint64;
      description
        "Number of entries currently in use for the resource.";
    }

    leaf committed {
      type uint64;
      description
        "Number of entries currently reserved for this resource. This is only
        relevant to tables which allocate a block of resource for a given
        feature.";
    }

    leaf free {
      type uint64;
      description
        "Number of entries available to use.";
    }

    leaf max-limit {
      type uint64;
      description
        "Maximum number of entries available for the resource. The value
        is the theoretical maximum resource utilization possible.";
    }

    leaf high-watermark {
      type uint64;
      description
        "A watermark of highest number of entries used for this resource.";
    }

    leaf last-high-watermark {
      type oc-types:timeticks64;
      description
        "The timestamp when the high-watermark was last updated. The value
        is the timestamp in nanoseconds relative to the Unix Epoch
        (Jan 1, 1970 00:00:00 UTC).";
    }

    leaf used-threshold-upper-exceeded {
      type boolean;
      description
        "This value is set to true when the used percentage value
        (used / (used + free) * 100) has crossed the used-threshold-upper for this
        resource and false when the used percentage value has crossed the configured
        used-threshold-upper-clear value for this resource.";
    }
  }

  grouping platform-resource-utilization-top {
    description
      "Top level of resource utilization.";

    container utilization {
      description
        "Resource utilization of the component.";

      container resources {
        description
          "Enclosing container for the resources in this component.";

        list resource {
          key "name";
          description
            "List of resources, keyed by resource name.";

          leaf name {
            type leafref {
              path "../config/name";
            }
            description
              "References the resource name.";
          }

          container config {
            description
              "Configuration data for each resource.";

            uses resource-utilization-config;
          }

          container state {
            config false;
            description
              "Operational state data for each resource.";

            uses resource-utilization-config;
            uses resource-utilization-state;
          }
        }
      }
    }
  }

  augment "/oc-platform:components/oc-platform:component/oc-platform:integrated-circuit" {
    description
      "Add resource utilization to integrated-circuit components.";
    uses platform-resource-utilization-top;
  }

  augment "/oc-platform:components/oc-platform:component/oc-platform:chassis" {
    description
      "Add resource utilization to chassis component.";
    uses platform-resource-utilization-top;
  }

  augment "/oc-platform:components/oc-platform:component/oc-linecard:linecard" {
    description
      "Add resource utilization to linecard components.";
    uses platform-resource-utilization-top;
  }
}
