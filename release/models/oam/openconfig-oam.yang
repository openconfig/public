module openconfig-oam {

  yang-version "1";

  // namespace
  namespace "http://openconfig.net/yang/oam";

  prefix "oc-oam";
  import openconfig-extensions { prefix oc-ext; }

 // google
  organization "OpenConfig working group";

  contact
    "OpenConfig working group
    www.openconfig.net";

  description
    "This module defines a YANG data model for configuring and managing
    EthernetOAM functions";

  oc-ext:openconfig-version "0.1.0";

  revision "2024-09-11" {
    description
      "Initial revision";
    reference "0.1.0";
  }

  grouping oam-top{
    description
      "top level grouping for configuration and operational state parameters relating
      to Ethernet OAM";

    container oam {
      description
        "Operational state and configuration parameters relating to
         Ethernet OAM";

      container config {
        description
          "Configuration parameters relating to Ethernet OAM";
      }
      container state {
        config false;
        description
          "Operational state parameters relating to Ethernet OAM";
      }
    }
  }

  uses oam-top;
}
