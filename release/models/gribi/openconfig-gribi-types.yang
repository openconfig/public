module openconfig-gribi-types {
  yang-version "1";
  namespace "http://openconfig.net/yang/gribi/types";
  prefix "oc-gribit";

  import openconfig-extensions {
    prefix oc-ext;
  }

  import openconfig-grpc-types {
    prefix oc-grpct;
  }

  organization
    "OpenConfig working group";
  contact
    "www.openconfig.net";

  description
    "";


  oc-ext:openconfig-version "0.1.0";
  oc-ext:catalog-organization "openconfig";
  oc-ext:origin "openconfig";

  revision 2024-04-23 {
    description
      "Initial revision.";
    reference "0.1.0";
  }

  identity GRIBI {
    base oc-grpct:GRPC_SERVICE;
    description
      "gNMI: gRPC Network Management Interface";
  }

}
