module openconfig-gnoi {
  yang-version "1";
  namespace "http://openconfig.net/yang/gnoi";
  prefix "oc-gnoi";

  import openconfig-extensions {
    prefix oc-ext;
  }

  import openconfig-system {
    prefix oc-sys;
  }

  import openconfig-system-grpc {
    prefix oc-sys-grpc;
  }

  import openconfig-grpc-services-common {
    prefix oc-grpc-common;
  }

  import openconfig-gnoi-types {
    prefix oc-gnoi-types;
  }

  organization
    "OpenConfig working group";
  contact
    "www.openconfig.net";

  description
    "";

  oc-ext:openconfig-version "0.1.0";
  oc-ext:catalog-organization "openconfig";
  oc-ext:origin "openconfig";

  revision 2024-04-23 {
    description
      "Initial revision.";
    reference "0.1.0";
  }

  grouping gnoi-base {
    description
      "";

    container gnoi {
      description
        "";

      uses oc-grpc-common:common-services;
    }
  }

  augment "/oc-sys:system/oc-sys-grpc:grpc-servers" +
          "/oc-sys-grpc:grpc-server/oc-sys-grpc:services" {
    when "../oc-sys-grpc:config/oc-sys-grpc:services = 'oc-gnoi-types:GNOI'";

    uses gnoi-base;
  }
}
