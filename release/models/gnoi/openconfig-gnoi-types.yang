module openconfig-gnoi-types {
  yang-version "1";
  namespace "http://openconfig.net/yang/gnoi/types";
  prefix "oc-gnoi-types";

  import openconfig-extensions {
    prefix oc-ext;
  }

  import openconfig-grpc-types {
    prefix oc-grpct;
  }

  organization
    "OpenConfig working group";
  contact
    "www.openconfig.net";

  description
    "This module contain";


  oc-ext:openconfig-version "0.1.0";
  oc-ext:catalog-organization "openconfig";
  oc-ext:origin "openconfig";

  revision 2024-04-23 {
    description
      "Initial revision.";
    reference "0.1.0";
  }

  identity GNOI {
    base oc-grpct:GRPC_SERVICE;
    description
      "gNOI: gRPC Network Operations Interface";
  }

}
