module openconfig-acl-defined-sets {

  yang-version "1";

  // namespace
  namespace "http://openconfig.net/yang/acl-defined-sets";

  prefix "oc-sets";

  import openconfig-extensions { prefix oc-ext; }
  import openconfig-inet-types { prefix oc-inet; }
  import openconfig-packet-match-types { prefix oc-pkt-match-types; }

  // meta
  organization "OpenConfig working group";

  contact
    "OpenConfig working group
    www.openconfig.net";

  description
    "This module defines configuration and operational state
    data for defined sets (IP prefixes lists, protocols, etc)
    to be used in network access control lists (i.e., filters,
    rules, etc.).";

  oc-ext:openconfig-version "1.0.0";

  revision "2022-07-12" {
    description
      "Initial version";
    reference "1.0.0";
  }

  // OpenConfig specific extensions for module metadata.
  oc-ext:catalog-organization "openconfig";
  oc-ext:origin "openconfig";

  grouping ipv4-prefix-sets-config {
    description "Configuration parameters of IPv4 prefix sets.";

    leaf name {
      type string;
      description
         "Name of the IPv4 prefix set to be used in the matches.";
    }

    leaf description {
      type string;
      description "A user defined IPv4 prefix set description.";
    }

    leaf-list prefix {
       type oc-inet:ipv4-prefix;
       description
         "A user defined list of IPv4 prefixes to be used in match
         conditions. Each entry is a IPv4 + mask combination.";
    }
  }

  grouping ipv6-prefix-sets-config {
    description "Configuration parameters of IPv6 prefix sets.";

    leaf name {
      type string;
      description
         "Name of the IPv6 prefix set to be used in the matches.";
    }

    leaf description {
      type string;
      description "A user defined IPv6 prefix list description.";
    }

    leaf-list prefix {
       type oc-inet:ipv6-prefix;
       description
         "A user defined list of IPv6 prefixes to be used in match
         conditions. Each entry is a IPv6 + mask combination.";
    }
  }

  grouping port-sets-config {
    description "Configuration parameters of port sets.";

    leaf name {
        type string;
        description
           "A user defined name of the port list to
            be used in the match condition.";
      }

      leaf description {
        type string;
        description
          "A user defined description
          for the port set";
      }

      leaf-list port {
        type oc-pkt-match-types:port-num-range;
         description
           "A user defined list of ports to be
           used in the match conditions.";
      }
  }

  grouping defined-sets-top {
    description "Configuration of Defined Sets.";

    container ipv4-prefix-sets {
      description
        "Container to hold list of IPv4
         prefixes which are matched as part of a policy.";

      list ipv4-prefix-set {
        key "name";
        description
          "List of IPv4 prefix sets.";

        leaf name {
          type leafref {
            path "../config/name";
          }
        description
          "Reference to prefix name list key.";
        }

        container config {
          description
            "Configuration data for prefix lists.";
          uses ipv4-prefix-sets-config;
        }

        container state {
          config false;
          description
            "State data for prefix lists.";
          uses ipv4-prefix-sets-config;
        }
      }
    }

    container ipv6-prefix-sets {
      description
        "Container to hold list of IPv6
         prefixes which are matched as part of a policy.";

      list ipv6-prefix-set {
        key "name";
        description "List of ipv6 prefix sets.";

        leaf name {
          type leafref {
            path "../config/name";
          }
        description  "Reference to prefix name list key.";
        }

        container config {
          description
          "Configuration data for prefix lists.";
          uses ipv6-prefix-sets-config;
        }

        container state {
          config false;
          description "State data for prefix lists.";
          uses ipv6-prefix-sets-config;
        }
      }
    }

    container port-sets {
      description
        "Data definitions for a list of ports which can
         be matched in policies.";

      list port-set {
        key "name";
        description
          "List of port set definitions.";

        leaf name {
          type leafref {
            path "../config/name";
          }
          description
            "Name of the portset -- this is used as a label to
             reference the set in match conditions.";
        }

        container config {
          description "Configuration data for port lists.";
          uses port-sets-config;
        }

        container state {
          config false;
          description "State data for port lists.";
          uses port-sets-config;
        }
      }
    }

  }



  grouping acl-defined-sets-top {
    description
      "Top level grouping for defined-sets";

    container defined-sets {
      description
        "Top level enclosing container for ACL model config
        and operational state data.";
      uses defined-sets-top;
    }
  }

  // data definition statements
  uses acl-defined-sets-top;

  // augment statements


}
