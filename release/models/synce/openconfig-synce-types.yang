module openconfig-synce-types {

    yang-version 1.1;

    namespace "http://openconfig.net/yang/openconfig-synce-types";

    prefix "oc-synce-types";

    import openconfig-extensions {
       prefix oc-ext;
    }

    // meta
    organization
      "OpenConfig working group";

    contact
      "OpenConfig working group
       www.openconfig.net";

    description
        "Typedefs for Synce module";

    oc-ext:openconfig-version "0.1.0";

    revision "2020-12-20" {
        description "Initial Version";
        reference "0.1.0";
    }

    typedef synce-external-interface-t {
        type enumeration {
            enum GPS {
                value 1;
                description "GPS interface as input-source";
            }
            enum 10MHZ_IN {
                value 2;
                description "10MHZ interface as input-source";
            }
            enum PTP {
                value 3;
                description "PTP interface as input-source";
            }
            enum BITS_T1 {
                value 4;
                description "BITS-T1 interface as input-source";
            }
            enum BITS_E1 {
                value 5;
                description "BITS-E1 interface as input-source";
            }
        }
        description "type definition for synce-external-interface-t";
    }

    typedef synce-sync-option-t {
        type enumeration {
            enum 1 {
                value 1;
                description "Networks optimized for the 2048 kbit/s hierarchy ";
            }
            enum 2 {
                value 2;
                description "Networks optimized for the 1544 kbit/s hierarchy that includes the rates 1544 kbit/s 6312 kbit/s and 44 736 kbit/s ";
            }
        }
        description "type definition for synce-sync-option-t";
    }

    typedef synce-clk-selection-mode-t {
        type enumeration {
            enum QL_ENABLED {
                value 1;
                description "Use the quality level as a criteria when selecting a clock ";
            }
            enum QL_DISABLED {
                value 2;
                description "Do not use the quality level as a criteria when selecting a clock";
            }
        }
        description "type definition for synce-clk-selection-mode-t";
    }

    typedef synce-autoneg-mode-t {
        type enumeration {
            enum MASTER {
                value 1;
                description "Configure 1000Base-T mode to master";
            }
            enum SLAVE {
                value 2;
                description "Configure 1000Base-T mode to slave";
            }
        }
        description "type definition for synce-autoneg-mode-t";
    }

    typedef synce-mode-option-t {
        type enumeration {
            enum SYNCHRONOUS {
                value 1;
                description "Configure the interface to synchronous mode";
            }
            enum NON_SYNCHRONOUS {
                value 2;
                description "Configure the interface to non-synchronous mode";
            }
        }
        description "type definition for synce-mode-option-t";
    }

    typedef synce-source-select-t {
        type enumeration {
            enum FORCE {
                value 1;
                description "Forcefully select a synchronization source";
            }
            enum MANUAL {
                value 2;
                description "manually select a synchronization source";
            }
        }
        description "type definition for synce-source-select-t";
    }

    typedef synce-signal-fail-t {
        type enumeration {
            enum ACTIVE {
                value 1;
                description "set to true";
            }
            enum NON_ACTIVE {
                value 2;
                description "set to false";
            }
        }
        description "type definition for synce-signal-fail-t";
    }

    typedef synce-is-src-selected-t {
        type enumeration {
            enum NO {
                value 0;
                description "Src is not seleceted";
            }
            enum YES {
                value 1;
                description "Src is seleceted";
            }
        }
        description "type definition for synce-is-src-selected-t";
    }

    typedef synce-is-sf-t {
        type enumeration {
            enum NO {
                value 0;
                description "Interface is not in Signal Fail condition";
            }
            enum YES {
                value 1;
                description "Interface is in Signal Fail condition";
            }
        }
        description "type definition for synce-is-sf-t";
    }

    typedef synce-external-cmds-t {
        type enumeration {
            enum NONE {
                value 0;
                description "No external commands configured";
            }
            enum LOCKOUT {
                value 1;
                description "Lockout external command configured";
            }
            enum FORCE {
                value 2;
                description "Force switch external command configured";
            }
            enum MANUAL {
                value 3;
                description "Manual switch external command configured";
            }
        }
        description "type definition for synce-external-cmds-t";
    }

    typedef synce-is-timer-running-t {
        type enumeration {
            enum NOT_RUNNING {
                value 0;
                description "Interface is not in Signal Fail condition";
            }
            enum RUNNING {
                value 1;
                description "Interface is in Signal Fail condition";
            }
        }
        description "type definition for synce-is-timer-running-t";
    }

    typedef synce-clock-state-t {
        type enumeration {
            enum NOT_APPLICABLE {
                value 0;
                description "N/A";
            }
            enum FREE_RUN {
                value 1;
                description "Clk is in Free-run state";
            }
            enum HOLDOVER {
                value 2;
                description "Clk is in Holdover state";
            }
            enum LOCKED {
                value 3;
                description "Clk is in Locked state";
            }
        }
        description "type definition for synce-clock-state-t";
    }

    typedef synce-esmc-state-t {
        type enumeration {
            enum IDLE {
                value 0;
                description "ESMC state is idle";
            }
            enum START {
                value 1;
                description "ESMC state is Start";
            }
            enum OK {
                value 2;
                description "ESMC state is OK";
            }
            enum FAILED {
                value 3;
                description "ESMC state is Failed";
            }
            enum NOT_APPLICABLE {
                value 4;
                description "ESMC state Not-Applicable";
            }
        }
        description "type definition for synce-esmc-state-t";
    }

    typedef synce-link-state-t {
        type enumeration {
            enum UP {
                value 1;
                description "Synce Interface is up";
            }
            enum DOWN {
                value 2;
                description "Synce Interface is down";
            }
        }
        description "type definition for synce-link-state-t";
    }

}
