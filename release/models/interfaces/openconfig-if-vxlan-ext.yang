module openconfig-if-vxlan-ext {

  yang-version "1";

  // namespace
  namespace "http://openconfig.net/yang/interfaces/vxlan-ext";

  prefix "oc-vxlan-ext";

  // import some basic types
  import openconfig-interfaces { prefix oc-if; }
  import openconfig-extensions { prefix oc-ext; }
  import openconfig-inet-types { prefix oc-inet; }
  import openconfig-yang-types { prefix oc-yang; }
  import ietf-interfaces { prefix ietf-if; }

  // meta
  organization "OpenConfig working group";

  contact
    "OpenConfig working group
    www.openconfig.net";

  description
    "This module adds VXLAN operational state model to
    support additional use cases.";

  oc-ext:openconfig-version "0.1.0";

  revision "2023-11-17" {
    description
    "Initial version of VXLAN extensions module to add counter stats";
    reference "0.1.0";
  }

  // OpenConfig specific extensions for module metadata.
  oc-ext:regexp-posix;
  oc-ext:catalog-organization "openconfig";
  oc-ext:origin "openconfig";

   identity vxlan {
     base ietf-if:interface-type;
     description
       "Virtual interface that facilitates the encapsulation, descapsulation,
       and transport of Layer 2 traffic over Layer 3 networks using the Virtual
       eXtensible LAN format described in RFC 7348";
     reference
       "RFC 7348 - Virtual eXtensible Local Area Network (VXLAN):
       A Framework for Overlaying Virtualized Layer 2 Networks
       over Layer 3 Networks";
  }

  grouping vxlan-intf-top {
    description
      "Grouping for defining the VXLAN(Virtual eXtensible Local Area Network) counters.";
    container vxlan {
      when "../config/type = 'vxlan'";
      config false;
      description
        "Top-level container for VXLAN(Virtual eXtensible Local Area Network) interface operational state.";
      container vteps {
        description
        "Enclosing container for the list of VTEPs(Virtual Tunnel End Point).";
        list vtep {
          description
            "The list of VTEP keyed by IP address.";
          key "vtep-ip";
          leaf vtep-ip {
            type leafref {
                path "../state/vtep-ip";
            }
          }
          container state {
            description
              "Operational state for a specific VTEP.";
              leaf vtep-ip {
                type oc-inet:ip-address;
                description
                  "VTEP IP address";
              }
              container counters {
                description
                  "Operational state regarding traffic encapsulated on local
                  device and directed towards a specific VTEP.";
                leaf total-encap-pkts {
                  type oc-yang:counter64;
                  description
                    "The total number of packets encapsulated on the local
                    device that are directed towards a specific VTEP.";
                }
                leaf total-encap-bytes {
                  type oc-yang:counter64;
                  description
                    "The total number of bytes encapsulated on the local
                    device that are directed towards a specific VTEP.";
                }
                leaf total-decap-pkts {
                  type oc-yang:counter64;
                  description
                    "The total number of packets from a specific VTEP
                    that are decapsulated on the local device.";
                }
                leaf total-decap-bytes {
                  type oc-yang:counter64;
                  description
                    "The total number of bytes from a specific VTEP
                    that are decapsulated on the local device.";
                }
                leaf unicast-decap-pkts {
                  type oc-yang:counter64;
                  description
                    "The total number of unicast packets from a specific VTEP
                    that are decapsulated on the local device.";
                }
                leaf bum-decap-pkts {
                  type oc-yang:counter64;
                  description
                    "The total number of BUM packets from a specific VTEP
                    that are decapsulated on the local device.";
                }
                leaf drop-decap-pkts {
                  type oc-yang:counter64;
                  description
                    "The total number of decapsulated packets from a specific VTEP
                    that have been dropped locally.";
                }
                leaf except-decap-pkts {
                  type oc-yang:counter64;
                  description
                    "The total number of decapsulated packets from a specific VTEP
                    that hit an exceptional condition.";
                }
              }
            }
         }
      }
    }
  }

  // augment statements

  augment "/oc-if:interfaces/oc-if:interface" {
    description
      "Add VXLAN encapsulation and decapsulation counters.";

    uses vxlan-intf-top;
  }
}
