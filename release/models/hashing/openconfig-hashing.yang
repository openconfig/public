module openconfig-hashing {
    yang-version "1";

    // namespace
    namespace "http://openconfig.net/yang/hashing";

    prefix "oc-hashing";

    // import some basic types
    import openconfig-extensions { prefix oc-ext; }

    // meta
    organization "OpenConfig working group";

    contact
      "OpenConfig working group
      netopenconfig@googlegroups.com";

    description
      "Model for managing hashing policies that would be referenced by the
      interfaces model.";


    oc-ext:openconfig-version "0.1.0";

    revision "2023-08-08" {
        description "Initial hashing model.";
        reference "0.1.0";
    }

    oc-ext:catalog-organization "openconfig";
    oc-ext:origin "openconfig";

    typedef hash-field-type-transport {
        type enumeration {
            enum NONE {
                description "Do not use any transport fields in the
                    calculation of the hash.";
            }
            enum SRC_PORT {
                description "Use only the source port from the
                    transport header in the calculation of the hash.";
            }
            enum DST_PORT {
                description "Use only the destination port from the
                    transport header in the calculation of the hash.";
            }
            enum BOTH {
                description "Use both the source and
                    destination ports from the transport header in
                    the calculation of the hash.";
            }
            enum TARGET_DEFINED {
                description "Use the default fields that are used by
                    the device for calculating the hash.";
            }
        }
        description "The transport layer fields that should be used to
            compute the hash.";
    }

    grouping hashing-inputs {
        description
            "Top level container for inputs to be used for hashing policies.";
        leaf transport-ports {
            type hash-field-type-transport;
            description "The transport layer fields that should be used to
                compute the hash.";
        }
    }

    grouping ipv4-fields-config {
        description "The IPv4 fields that should be used to
            compute the hash.";
        leaf ipv4-none {
            type boolean;
            description "Do not use any IPv4 fields in the
                calculation of the hash.";
        }
        leaf ipv4-src-address {
            type boolean;
            description "Use only the IPv4 source address in the
                calculation of the hash.";
        }
        leaf ipv4-dst-address {
            type boolean;
            description "Use only the IPv4 destination address in the
                calculation of the hash.";
        }
        leaf ipv4-both {
            type boolean;
            description "Use both the IPv4 source and
                destination addresses in the calculation of the
                hash.";
        }
        leaf ipv4-target-define {
            type boolean;
            description "Use the default fields that are used by
                the device for calculating the hash.";
        }
        leaf ipv4-ingress-subinterface {
            type boolean;
            description "Use the ingress subinterface identifired
                in the calculation of the hash.";
        }
    }

    grouping ipv4-fields-top {
        description
            "Top-level container of hashing input for ipv4";
        container config {
            description
                "Configuration data of hashing input for ipv6";
            uses ipv4-fields-config;
        }
        container state {
            description
                "Operational data of hashing input for ipv6";
            config false;
            uses ipv4-fields-config;
        }
    }

    grouping ipv6-fields-config {
        description "The IPv6 fields that should be used to
            compute the hash.";
        leaf ipv6-none {
            type boolean;
            description "Do not use any IPv6 fields in the
                calculation of the hash.";
        }
        leaf ipv6-src-address {
            type boolean;
            description "Use only the IPv6 source address in the
                calculation of the hash.";
        }
        leaf ipv6-dst-address {
            type boolean;
            description "Use only the IPv6 destination address in the
                calculation of the hash.";
        }
        leaf ipv6-both {
            type boolean;
            description "Use both the IPv6 source and
                destination addresses in the calculation of the
                hash.";
        }
        leaf ipv6-target-define {
            type boolean;
            description "Use the default fields that are used by
                the device for calculating the hash.";
        }
        leaf ipv6-flow-label {
            type boolean;
            description "Use the flow label in the IPv6 header
                to calculate the hash.";
        }
        leaf ipv6-ingress-subinterface {
            type boolean;
            description "Use the ingress subinterface identifired in the
                calculation of the hash.";
        }
    }

    grouping ipv6-fields-top {
        description
            "Top-level container of hashing input for ipv4";
        container config {
            description
                "Configuration data of hashing input for ipv4";
            uses ipv6-fields-config;
        }
        container state {
            description
                "Operational data of hashing input for ipv4";
            config false;
            uses ipv6-fields-config;
        }
    }

    grouping hashing-policy-config {
        description
          "Configuration data for hashing policies.";

        leaf name {
            type string;
            description
              "The name of the hashing policy.
              When a configured user-controlled policy is created by the
              system, it is instantiated with the same name in the
              /system/hashing-policies/hashing-policy/name list.";
        }

        leaf rotation {
            type uint64;
            description
                "The number of bits to rotate the output of the hash algorithm by
                in order to get the final computed hash value. Ref: BCM56998
                Programming Guide, 6.3.8 Hash Bits Selection.";
        }

        leaf seed {
            type uint64;
            description
                "The seed used to initialize the hash algorithm";
        }

        leaf algorithm {
            type string;
            description
                "The name of hash algorithm. This algorithm MUST
                be a supported algorithm";
        }
    }

    grouping hashing-top {
        description
            "Top level grouping for hashing configuration and operational state
            data.";

        container hashing-policies {
            description
              "Top level container for hashing, including configuration and
              state data.";

            list hashing-policy {
                key "name";

                description
                  "The list of named policies to be used on the device.";

                leaf name {
                    type leafref {
                        path "../config/name";
                    }
                    description
                      "References the name of the hashing policy.";
                }
                container config {
                    description
                      "Configurable items at the global hash policy level.";

                    uses hashing-policy-config;
                }
                container state {
                    config false;
                    description
                      "Operational state data at the global hash policy
                      level.";

                    uses hashing-policy-config;
                }
                container hash-field-modes {
                    description
                        "Container for specifying inputs to be used when
                        calculating the hash.";
                    container config {
                        description
                            "Configurable items at the hashing inputs level.";
                        uses hashing-inputs;
                    }
                    container state {
                        config false;
                        description "Operational state data at the hashing
                            inputs level.";
                        uses hashing-inputs;
                    }
                    container ipv4-fields {
                        description "ipv4 hashing input fields.";
                        uses ipv4-fields-top;
                    }
                    container ipv6-fields {
                        description "ipv6 hashing input fields.";
                        uses ipv6-fields-top;
                    }
                }
            }
        }
    }

    grouping supported-algorithms-state {
        description
            "Top-level container for the supported algorithms.";
        leaf name {
            type string;
            description
                "Name of the supported algorithm.";
        }
        leaf description {
            type string;
            description
                "Description of the supported algorithm.";
        }
    }
    grouping supported-algorithms-top {
        description
            "Top-level container of the supported algorithms for supported
            algorithms.  The list of algorithms are expected to be defined by
            the target device.";
        container supported-algorithms {
            config false;
            description
                "Container of the supported algorithms for supported
                algorithms.";
            list supported-algorithm {
                key "name";

                description
                    "List of the supported algorithms for supported
                    algorithms.";
                
                leaf name {
                    type leafref {
                        path "../state/name";
                    }
                    description
                        "Reference to the supported algorithm list key.";
                }

                container state {
                    description
                        "Operational data for the supported algorithm.";
                    config false;
                    uses supported-algorithms-state;
                }
            }
        }

    }

    uses supported-algorithms-top;
    uses hashing-top;
}
