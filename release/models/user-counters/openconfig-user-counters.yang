module openconfig-user-counters {
  yang-version 1;
  namespace "http://openconfig.net/yang/user-counters";
  prefix "oc-user-counters";

  import openconfig-extensions {
    prefix "oc-ext";
  }
  import openconfig-yang-types {
    prefix "oc-yang";
  }

  organization
    "OpenConfig working group";

  contact
    "OpenConfig working group
     www.openconfig.net";

  description
    "This module defines a top-level container for user-defined counters.
     These counters can be referenced by other OpenConfig models to allow
     users to track statistics for specific policies, rules, or other
     configuration entities.";

  oc-ext:openconfig-version "0.1.0";

  revision "2025-12-16" {
    description
      "Initial release of the user-counters model.";
    reference
      "0.1.0";
  }

  // OpenConfig specific extensions for module metadata.
  oc-ext:catalog-organization "openconfig";
  oc-ext:origin "openconfig";

  grouping user-counters-top {
    description
      "Top-level grouping for user-defined counters.";

    container user-counters {
      description
        "Top-level container for user-defined counters.";

      list user-counter {
        key "name";

        description
          "A user-defined counter. It can be used for counting packets or
           bytes for a particular feature, e.g., a policy forwarding rule.";

        leaf name {
          type leafref {
            path "../config/name";
          }
          description
            "Reference to the name of the user-defined counter.";
        }

        container config {
          description
            "Configuration parameters for the user-defined counter.";

          leaf name {
            type string;
            description
              "A unique name for the user-defined counter.";
          }
        }

        container state {
          config false;
          description
            "Operational state parameters for the user-defined counter.";

          leaf name {
            type string;
            description
              "A unique name for the user-defined counter.";
          }

          container counters {
            description
              "A container for the counter values.";
            leaf value {
              type oc-yang:counter64;
              description
                "The current value of the user-defined counter.";
            }
          }
        }
      }
    }
  }


  uses user-counters-top;

}
