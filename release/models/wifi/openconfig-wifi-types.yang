module openconfig-wifi-types {

  yang-version "1";

  // namespace
  namespace "http://openconfig.net/yang/wifi/wifi-types";

  // Assign this module a prefix to be used by other modules, when imported.
  prefix "oc-wifi-types";

  import openconfig-extensions { prefix oc-ext; }

  // Some required meta
  organization "OpenConfig working group";

  contact
    "OpenConfig working group
    www.openconfig.net";

  description
    "This module contains a set of WiFi-specific type definitions
    that are used in the openconfig-wifi modules. It can be
    imported by any module to make use of these types.";

  oc-ext:openconfig-version "1.1.4";

  revision "2025-11-03" {
    description "Add a WiFi protocol identity";
    reference "1.1.4";
  }

  revision "2024-04-25" {
    description
      "Adding INACTIVE client_state";
    reference "1.1.3";
  }

  revision "2023-09-01" {
    description
      "Adding FREQ_2_6_GHZ.";
    reference "1.1.2";
  }

  revision "2022-05-26" {
    description
      "Fix typos in descriptions.";
    reference "1.1.1";
  }

  revision "2022-03-24" {
    description
      "Update model to support operation in 6 GHz frequency.";
    reference "1.1.0";
  }

  revision "2021-08-02" {
    description
      "Add OFDMA in client capabilities.";
    reference "1.0.0";
  }

  revision "2020-05-19" {
    description
      "Update namespace per new directory structure.";
    reference "0.1.2";
  }

  revision "2020-03-24" {
    description
      "Update namespace and fix BETTER_CHANNEL enum.";
    reference "0.1.1";
  }

  revision "2017-07-25" {
    description
      "Initial revision.";
    reference "0.1.0";
  }

  //typdef statements
  typedef channels-type {
    type uint8 {
      range "1..14 | 17 | 21 | 25 | 29 | 33 | 36 | 37 | 40 | 41 | 44 | 45 | 48 | 49 | 52 | 53 | 56 | 57 | 60 | 61 | 64 | 65 | 69 | 73 | 77 | 81 | 85 | 89 | 93 | 97 | 100 | 101 | 104 | 105 | 108 | 109 | 112 | 113 | 116 | 117 | 120 | 121 | 124 | 125 | 128 | 129 | 132 | 133 | 136 | 137 | 140 | 141 | 144 | 145 | 149 | 153 | 157 | 161 | 165 | 169 | 173 | 177 | 181 | 185 | 189 | 193 | 197 | 201 | 205 | 209 | 213 | 217 | 221 | 225 | 229 | 233";
    }
    description
      "Type to specify all the WiFi channels available for use. This is
      a superset of what may be allowed by any one particular regulatory
      domain.";
  }

  // identity statements
  identity CLIENT_STATE {
    description
      "Base type to specify the current state of a Client.";
  }

  identity ASSOCIATED {
    base CLIENT_STATE;
    description
      "Client has finished 802.11 Association phase. This implies 'Open' system,
      or 802.11 Authentication complete.";
  }

  identity L2AUTH_REQD {
    base CLIENT_STATE;
    description
      "Client has Associated, but not L2 Authenticated (e.g. 802.1X)";
  }

  identity L3AUTH_REQD {
    base CLIENT_STATE;
    description
      "Client has Associated, but not L3 Authenticated (e.g. Captive Portal).";
  }

  identity DHCP_REQD {
    base CLIENT_STATE;
    description
      "Client has Associated & Authenticated, but has not obtained IP address.";
  }

  identity AUTHENTICATED {
    base CLIENT_STATE;
    description
      "Client has fully Authenticated & permitted to access network resources.";
  }

  identity L2AUTH_FAILURE_REJECT {
    base CLIENT_STATE;
    description
      "L2 failure, due to RADIUS Access-Reject.";
  }

  identity L2AUTH_FAILURE_TIMEOUT {
    base CLIENT_STATE;
    description
      "L2 failure, due to RADIUS timeout.";
  }

  identity L3AUTH_FAILURE {
    base CLIENT_STATE;
    description
      "L3 failure. Could be incorrect CP credentials or higher layer
      Captive Portal issues.";
  }

  identity DHCP_FAILURE {
    base CLIENT_STATE;
    description
      "Client has Associated & Authenticated but has failed to receive an IP
      address, utilizing DHCP.";
  }

  identity POWERSAVE {
    base CLIENT_STATE;
    description
      "AP has received a PS frame, indicating the client is currently in a
      powersave state.";
  }

  identity BLACKLISTED {
    base CLIENT_STATE;
    description
      "This client has been blacklisted, through either L2 (MAC) or higher-level
      (signature) mechanisms.";
  }

  identity INACTIVE {
    base CLIENT_STATE;
    description
      "Client is no longer active in the 802.11 state machine. Client data
      remains in the client state, but client is no longer active on AP.";
  }

  identity AP_STATE {
    description "The Up/Down state of an AP.";
  }

  identity UP {
    base AP_STATE;
    description
      "The AP is in the up state.";
  }

  identity DOWN {
    base AP_STATE;
    description
      "The AP is in the down state.";
  }

  identity UPGRADING {
    base AP_STATE;
    description
      "The AP is in the Downgrading firmware state.";
  }

  // Possible basic-rates are: 1, 2, 5.5, 6, 9, 11, 12, 18, 24, 36, 48, 54 //
  identity DATA_RATE {
    description "base type to specify available Data-rates.";
  }

  identity RATE_1MB {
    base DATA_RATE;
    description "1 Mbps DSSS PHY.";
  }

  identity RATE_2MB {
    base DATA_RATE;
    description "2 Mbps DSSS PHY.";
  }

  identity RATE_5.5MB {
    base DATA_RATE;
    description "5.5 Mbps DSSS PHY.";
  }

  identity RATE_6MB {
    base DATA_RATE;
    description "6 Mbps OFDM PHY.";
  }

  identity RATE_9MB {
    base DATA_RATE;
    description "9 Mbps OFDM PHY.";
  }

  identity RATE_11MB {
    base DATA_RATE;
    description "11 Mbps DSSS PHY.";
  }

  identity RATE_12MB {
    base DATA_RATE;
    description "12 Mbps OFDM PHY.";
  }

  identity RATE_18MB {
    base DATA_RATE;
    description "18 Mbps OFDM PHY.";
  }

  identity RATE_24MB {
    base DATA_RATE;
    description "24 Mbps OFDM PHY.";
  }

  identity RATE_36MB {
    base DATA_RATE;
    description "36 Mbps OFDM PHY.";
  }

  identity RATE_48MB {
    base DATA_RATE;
    description "48 Mbps OFDM PHY.";
  }

  identity RATE_54MB {
    base DATA_RATE;
    description "54 Mbps OFDM PHY.";
  }

  identity OPERATING_FREQUENCY {
    description "Operating frequency of a Radio or SSID.";
  }

  identity FREQ_2GHZ {
    base OPERATING_FREQUENCY;
    description "The Radio or SSID will operate at 2.4GHz only.";
  }

  identity FREQ_5GHZ {
  base OPERATING_FREQUENCY;
  description "The Radio or SSID will operate at 5GHz only.";
  }

  identity FREQ_2_5_GHZ {
    base OPERATING_FREQUENCY;
    description
      "The Radio or SSID will be dual-band; operating in
      both 2.4 & 5GHz frequencies.";
  }

  identity FREQ_6GHZ {
    base OPERATING_FREQUENCY;
    description "The Radio or SSID will operate at 6GHz only.";
  }

  identity FREQ_5_6_GHZ {
    base OPERATING_FREQUENCY;
    description "The Radio or SSID will be dual-band; operating in both 5 &
    6GHz frequencies.";
  }

  identity FREQ_2_5_6_GHZ {
    base OPERATING_FREQUENCY;
    description "The Radio or SSID will be tri-band; operating in 2.4, 5 and
    6GHz frequencies.";
  }

  identity FREQ_2_6_GHZ {
    base OPERATING_FREQUENCY;
    description "The Radio or SSID will be dual band; operating in 2.4 and
    6GHz frequencies.";
  }

  identity CLIENT_CAPABILITIES {
    description
      "Client capabilities, as reported by Association Request or
      Probe Request frames.";
  }

  identity MU_BEAMFORMER {
    base CLIENT_CAPABILITIES;
    description "Whether this STA can MU-MIMO Beamform.";
  }

  identity MU_BEAMFORMEE {
    base CLIENT_CAPABILITIES;
    description "Whether this STA can Rx MU-MIMO Beamformed frames.";
  }

  identity OFDMA {
    base CLIENT_CAPABILITIES;
    description "Whether this STA can use OFDMA.";
  }

  identity DOT_11R {
    base CLIENT_CAPABILITIES;
    description
      "Whether this STA supports 802.11r. Note, must be
      enabled on BSS for this to be accurate.";
  }

  identity DOT_11V {
    base CLIENT_CAPABILITIES;
    description
      "Whether this STA supports 802.11v BSS Transition. Note, must
      be enabled on BSS for this to be accurate; unless Probe Request
      are observed in addition to Association Request.";
  }

  identity MFP {
    base CLIENT_CAPABILITIES;
    description "Whether this STA can use Management Frame Protection.";
  }

  identity CHANGE_REASON_TYPE {
    description
      "Base type to specify the reason an Access Point
      has changed channels.";
  }
  identity DFS {
    base CHANGE_REASON_TYPE;
    description
      "DFS hit occurred.";
  }

  identity NOISE {
    base CHANGE_REASON_TYPE;
    description
      "Excessive amounts of non-802.11 Noise occurred.";
  }

  identity ERRORS {
    base CHANGE_REASON_TYPE;
    description
      "Excessive reception of frames which
      failed the FCS occurred.";
  }

  identity BETTER_CHANNEL {
    base CHANGE_REASON_TYPE;
    description
      "A less utilized channel exists. eg CCI avoidance
       led to this channel-change.";
  }
  // Extend channel-change reasons here, when applicable.

  identity WIFI_PROTOCOL {
    description "Operating frequency of a Radio or SSID.";
  }

  identity WIFI_80211_A {
    base WIFI_PROTOCOL;
    description "802.11a WiFi Protocol.";
  }

  identity WIFI_80211_B {
    base WIFI_PROTOCOL;
    description "802.11b WiFi Protocol";
  }

  identity WIFI_80211_G {
    base WIFI_PROTOCOL;
    description "802.11g WiFi Protocol";
  }

  identity WIFI_80211_N {
    base WIFI_PROTOCOL;
    description "802.11n WiFi Protocol";
  }

  identity WIFI_80211_AC {
    base WIFI_PROTOCOL;
    description "802.11ac WiFi Protocol";
  }

  identity WIFI_80211_AX {
    base WIFI_PROTOCOL;
    description "802.11ax WiFi Protocol";
  }

  identity WIFI_80211_BE {
    base WIFI_PROTOCOL;
    description "802.11be WiFi Protocol";
  }
}
