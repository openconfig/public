module openconfig-system-wifi-ext {

  yang-version "1";

  namespace "http://openconfig.net/yang/wifi";

  // Assign this module a prefix to be used by other modules, when imported.
  prefix "oc-system-wifi-ext";
  // Imports
  import openconfig-yang-types { prefix oc-yang; }
  import openconfig-extensions { prefix oc-ext; }
  import openconfig-inet-types { prefix oc-inet; }
  // WiFi types
  import openconfig-wifi-types { prefix oc-wifi; }
  // Original model this is augmenting
  import openconfig-system { prefix "oc-sys"; }

  // Some required meta
  organization "OpenConfig working group";

  contact
    "OpenConfig working group
    www.openconfig.net";

  description
    "Model for managing Controller-specific Config & State for
    system-level elements. This explicitly excludes any 802.11
    MAC/PHY layer elements.";

  oc-ext:openconfig-version "0.2.0";

  revision "2017-10-01" {
    description
      "Add country-code and hostname to MAC.";
    reference "0.2.0";
  }

  revision "2017-07-25" {
    description
      "Initial revision";
    reference "0.1.0";
  }

  // grouping statements

  grouping assigned-controllers-config {
    description
      "Controller(s) an AP may join. If cloud controller, this will be
      the cloud instance(s). This config is applied to APs, not Controllers,
      which is in-line with APs being the top-level network element.";

    leaf id {
      type string;
      description
        "id serves as a reference point to the [1-n] Controller(s) this AP
        is assigned to.";
      }

    leaf fqdn {
      type oc-inet:domain-name;
      description
        "The FQDN of a Controller this AP is assigned to. The list should be
        ordered, according to priority. eg Primary first,
        Secondary second, Tertiary third etc.";
    }

    leaf controller-ipv4-address {
      type oc-inet:ipv4-address;
      description
        "IPv4 address of Controller for this AP. The list should be
        ordered, according to priority. eg. Primary first, Secondary second,
        Tertiary third etc.";
    }

    leaf-list controller-ipv6-address {
      type oc-inet:ipv6-address;
      description
        "IPv6 address of Controller for this AP. The list should be
        ordered, according to priority. eg. Primary first, Secondary second,
        Tertiary third etc.";
    }
  }

  // Note, configuration of both AP & Controller system parameters, such as
  // NTP & IP utilizes parent model (openconfig-system.yang)
  grouping controller-aps-system-config {
    description
      "Grouping for Controller & AP system configuration.";

    leaf mac {
      type oc-yang:mac-address;
      description
        "MAC address of the AP primary Ethernet interface. If AP
        has multiple Ethernet interfaces, this would be the MAC printed
        on the unit label and referenced within the management system.
        Vendors MUST reject attempts to configure this leaf.";
    }

    leaf hostname {
      type oc-inet:domain-name;
      description
        "Hostname of the Access Point.";
    }

    leaf country-code {
      type string {
        pattern '[a-zA-Z]{2}';
        }
      description
        "Country code where the AP operates in ISO 3166-1 alpha-2
        representation";
    }
  }

  grouping controller-aps-system-state {
    description
      "Grouping for a Controller & AP system state data.";

    leaf domain-name {
      type oc-inet:domain-name;
      description
        "FQDN of the Access Point.";
    }

    leaf opstate {
      type identityref {
        base oc-wifi:AP_STATE;
      }
      description
        "The current operational state of the AP.";
    }

    leaf uptime {
      type uint32;
      units seconds;
      description
        "Seconds this AP has been in the op-state of 'Up'.";
    }

    leaf enabled {
      type boolean;
      description
        "Wheather the AP is enabled or disabled.";
    }

    leaf serial {
      type string;
      description
        "Serial number of the Access Point.";
    }

    leaf model {
      type string;
      description
        "Model number of the Access Point.";
    }

    leaf ipv4 {
      type oc-inet:ipv4-address;
      description
        "The IPv4 address of the Access Point.";
    }

    leaf ipv6 {
      type oc-inet:ipv6-address;
      description
        "The IPv6 address of the Access Point.";
    }

    leaf power-source {
      type enumeration {
      enum AT {
        description "Powered using 802.3at.";
      }
      enum AF {
        description "Powered using 802.3af.";
      }
      enum PLUG {
        description "Powered using local source, not PoE.";
      }
    }
    description
      "Enumerate how the AP is being powered.";
    }
  }

  grouping controller-aps-system-top {
    description
      "Top-level grouping for APs assigned to controller(s).";

    container joined-aps {
      description
        "Top most container for joined-aps.";

      list joined-ap {
        key "mac";
        description
          "List of access points that have joined the controller.";

        leaf mac {
          type leafref {
            path "../config/mac";
          }
          description
          "Reference to the MAC address list key.";
        }

        container config {
          description
            "Config container for Joined APs.";

          uses controller-aps-system-config;
        }

        container state {
          config false;
          description
            "State container for Joined APs.";

          uses controller-aps-system-config;
          uses controller-aps-system-state;
        }
      }
    }
  }

  grouping controller-ap-parameters-top {
    description
      "Top-level grouping for assigning AP's to Controller(s).";

    container ap-assigned-controllers {
      description
        "Wireless Controller(s) this AP is assigned to. eg. Primary
        Secondary, Tertiary etc. This is config & state applied to an AP;
        not used for Controller state (eg 'joined-aps' are below).";

      list controller {
        key "id";
        description
          "Controller(s) this AP is assinged to, referenced by id.";

        leaf id {
          type leafref {
            path "../config/id";
          }
          description
            "id serves as a reference point to the [1-n] Controller(s) this AP
            is assigned to.";
        }

        container config {
          description
            "Config. container for assigning APs to Controllers.";

          uses assigned-controllers-config;
        }

        container state {
          config false;
          description
            "State container for APs assigned to Controllers.";

          uses assigned-controllers-config;
        }
      }
    }
  }

  augment "/oc-sys:system" {
  description
    "Augmentation to opeconfig-system.yang to include WiFi Controller.";

  uses controller-ap-parameters-top;
  uses controller-aps-system-top;
  }
}
