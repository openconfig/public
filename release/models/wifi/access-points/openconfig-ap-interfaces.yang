module openconfig-ap-interfaces {

  yang-version "1";

  // namespace
  namespace "http://openconfig.net/yang/wifi/interfaces";

  // Assign this module a prefix to be used by other modules, when
  // imported.
  prefix "oc-ap-if";

  // Imports
  import openconfig-extensions { prefix oc-ext; }
  import openconfig-interfaces { prefix oc-if; }
  import openconfig-access-points { prefix oc-access-points; }
  import openconfig-if-ethernet { prefix oc-eth; }
  import openconfig-if-aggregate {prefix oc-lag; }
  import openconfig-if-poe {prefix oc-poe; }
  import openconfig-vlan {prefix oc-vlan; }
  import openconfig-if-tunnel {prefix oc-tun; }
  import openconfig-if-ip {prefix oc-ip; }
  import openconfig-if-8021x {prefix oc-1x; }

  // Meta
  organization "OpenConfig working group";

  contact
    "OpenConfig working group
    www.openconfig.net";

  description
    "This module defines the configuration and state data for
    non-radio interfaces on WiFi Access Points.";

  oc-ext:openconfig-version "0.1.0";

  revision "2019-05-29" {
    description
      "Initial version.";
    reference "0.1.0";
  }

  grouping ap-interfaces-top {
    description
      "Top-level grouping for AP interface configuration and
      operational state data";

    container interfaces {
      description
        "Top level container for non-radio AP interfaces, including
        configuration and state data.";

      list interface {
        key "name";

        description
          "The list of named interfaces on the device.";

        leaf name {
          type leafref {
            path "../config/name";
          }
          description
            "References the name of the interface";
        }

        container config {
          description
            "Configurable items at the global, physical interface
            level";
          oc-ext:telemetry-on-change;

          uses oc-if:interface-phys-config;
        }

        container state {

          config false;
          description
            "Operational state data at the global interface level";

          uses oc-if:interface-phys-config;
          uses oc-if:interface-common-state;
          uses oc-if:interface-counters-state;
        }
      }
    }
  }

  // augment statements
  augment "/oc-access-points:access-points/" +
    "oc-access-points:access-point" {
    description
      "Adds interface configuration and state to access-points model";

    uses ap-interfaces-top;
  }

  augment "/oc-access-points:access-points/" +
    "oc-access-points:access-point/oc-ap-if:interfaces/" +
    "oc-ap-if:interface" {
    description
      "Adds ethernet interface configuration and state to
      access-points model";

    uses oc-eth:ethernet-top;
  }

  augment "/oc-access-points:access-points/" +
    "oc-access-points:access-point/oc-ap-if:interfaces/" +
    "oc-ap-if:interface/oc-ap-if:ethernet" {
    description
        "Adds 802.1X settings to individual Ethernet interfaces";

      uses oc-1x:dot1x-top;
  }

  augment "/oc-access-points:access-points/" +
    "oc-access-points:access-point/oc-ap-if:interfaces/" +
    "oc-ap-if:interface/oc-ap-if:ethernet/oc-ap-if:switched-vlan" {
    description
      "Adds vlan-map to switched-vlans.";

    uses oc-1x:vlan-map-top;
  }

  augment "/oc-access-points:access-points/" +
    "oc-access-points:access-point/oc-ap-if:interfaces/" +
    "oc-ap-if:interface" {
    description
      "Adds subinterface configuration and state to
      access-points model";

    uses oc-if:subinterfaces-top;
  }

  augment "/oc-access-points:access-points/" +
    "oc-access-points:access-point/oc-ap-if:interfaces/" +
    "oc-ap-if:interface/oc-ap-if:subinterfaces/oc-ap-if:subinterface" {
    description
      "IPv4 address family configuration for
      interfaces";

    uses oc-ip:ipv4-top;
  }

  augment "/oc-access-points:access-points/" +
    "oc-access-points:access-point/oc-ap-if:interfaces/" +
    "oc-ap-if:interface/oc-ap-if:subinterfaces/oc-ap-if:subinterface" {
    description
      "IPv6 address family configuration for
      interfaces";

    uses oc-ip:ipv6-top;
  }

  augment "/oc-access-points:access-points/" +
    "oc-access-points:access-point/oc-ap-if:interfaces/" +
    "oc-ap-if:interface" {
    description
      "Adds lag configuration and state to access-points model";

    uses oc-lag:aggregation-logical-top;
  }

  augment "/oc-access-points:access-points/" +
    "oc-access-points:access-point/oc-ap-if:interfaces/" +
    "oc-ap-if:interface/oc-ap-if:ethernet" {
    description
      "Adds poe configuration and state to access-points model";

    uses oc-poe:poe-ethernet-top;
  }

  augment "/oc-access-points:access-points/" +
    "oc-access-points:access-point/oc-ap-if:interfaces/" +
    "oc-ap-if:interface/oc-ap-if:ethernet" {
    description
      "Adds vlan configuration and state to ethernet interfaces.";

    uses oc-vlan:vlan-switched-top;
  }

  augment "/oc-access-points:access-points/" +
    "oc-access-points:access-point/oc-ap-if:interfaces/" +
    "oc-ap-if:interface/oc-ap-if:aggregation" {
    description
      "Adds vlan configuration and state to lag interfaces.";

    uses oc-vlan:vlan-switched-top;
  }

  augment "/oc-access-points:access-points/" +
    "oc-access-points:access-point/oc-ap-if:interfaces/" +
    "oc-ap-if:interface" {
    description
      "Adds tunnel configuration and state to access-points model";

    uses oc-tun:tunnel-top;
  }
  // Deviation statements
  // Unnumbered interfaces not supported on Access Points.
  deviation "/oc-access-points:access-points/" +
    "oc-access-points:access-point/" +
    "oc-ap-if:interfaces/oc-ap-if:interface/" +
    "oc-ap-if:subinterfaces/oc-ap-if:subinterface/oc-ap-if:ipv4/" +
    "oc-ap-if:unnumbered" {
    deviate not-supported;
  }

  deviation "/oc-access-points:access-points/" +
    "oc-access-points:access-point/" +
    "oc-ap-if:interfaces/oc-ap-if:interface/" +
    "oc-ap-if:subinterfaces/oc-ap-if:subinterface/oc-ap-if:ipv6/" +
    "oc-ap-if:unnumbered" {
    deviate not-supported;
  }

  deviation "/oc-access-points:access-points/" +
    "oc-access-points:access-point/" +
    "oc-ap-if:interfaces/oc-ap-if:interface/" +
    "oc-ap-if:tunnel/oc-ap-if:ipv4/oc-ap-if:unnumbered" {
    deviate not-supported;
  }

  deviation "/oc-access-points:access-points/" +
    "oc-access-points:access-point/" +
    "oc-ap-if:interfaces/oc-ap-if:interface/" +
    "oc-ap-if:tunnel/oc-ap-if:ipv6/oc-ap-if:unnumbered" {
    deviate not-supported;
  }
}
