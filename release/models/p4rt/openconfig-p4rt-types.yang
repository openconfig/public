module openconfig-p4rt-types {
  yang-version "1";
  namespace "http://openconfig.net/yang/p4rt/types";
  prefix "oc-p4rt-types";

  import openconfig-extensions { prefix oc-ext; }
  import openconfig-grpc-types { prefix oc-grpct; }

  organization
    "OpenConfig Working Group";

  contact
    "www.openconfig.net";

  description
    "";

  oc-ext:openconfig-version "0.1.0";

  revision 2024-03-10 {
    description
      "Initial revision.";
    reference "0.1.0";
  }

  identity P4RT {
    base "oc-grpct:GRPC_SERVICE";
    description
      "P4RT: P4 Runtime (P4RT) Service.";
  }
}
