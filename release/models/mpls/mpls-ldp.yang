module mpls-ldp {

  yang-version "1";

  // namespace
  namespace "http://openconfig.net/yang/ldp";

  prefix "ldp";

  // import some basic types
  import ietf-inet-types { prefix inet; }
  import mpls-types { prefix mplst; }


  // meta
  organization "OpenConfig working group";

  contact
    "OpenConfig working group
    netopenconfig@googlegroups.com";

  description
    "Configuration of Label Distribution Protocol global and LSP-
    specific parameters for IGP-congruent LSPs";

  oc-ext:openconfig-version "0.2.0";

  revision "2015-10-14" {
    description
      "Work in progress";
    reference "0.2.0";
  }

  revision "2015-07-04" {
    description
      "Work in progress";
    reference "Pre-release";
  }

  // feature statements

  // identity statements

  // typedef statements

  // grouping statements

   grouping ldp-global {
    description "global LDP signaling configuration";

    container ldp {
      description "LDP global signaling configuration";

      container timers {
        description "LDP timers";
      }
    }
  }


  grouping igp-tunnel-ldp {
    description "common defintiions for LDP-signaled LSP tunnel
    types";

    container tunnel {
      description "contains configuration stanzas for different LSP
      tunnel types (P2P, P2MP, etc.)";

      leaf tunnel-type {
        type mplst:tunnel-type;
          description "specifies the type of LSP, e.g., P2P or P2MP";
      }

      leaf ldp-type {
        type enumeration {
          enum BASIC {
            description "basic hop-by-hop LSP";
          }
          enum TARGETED {
            description "tLDP LSP";
          }
        }
        description "specify basic or targeted LDP LSP";
      }

      container p2p-lsp {
        when "tunnel-type = 'P2P'" {
          description "container active when LSP tunnel type is
          point to point";
        }

        description "properties of point-to-point tunnels";

        leaf-list fec-address {
          type inet:ip-prefix;
          description "Address prefix for packets sharing the same
          forwarding equivalence class for the IGP-based LSP";
        }
      }

      container p2mp-lsp {
        when "tunnel-type = 'P2MP'" {
          description "container is active when LSP tunnel type is
          point to multipoint";
        }

        description "properties of point-to-multipoint tunnels";

        // TODO: specify group/source, etc.

      }

      container mp2mp-lsp {
        when "tunnel-type = 'MP2MP'" {
          description "container is active when LSP tunnel type is
          multipoint to multipoint";
        }

        description "properties of multipoint-to-multipoint tunnels";

        // TODO: specify group/source, etc.

      }
    }
  }

  grouping igp-lsp-ldp-setup {
    description "grouping for LDP setup attributes";

    container ldp {

      presence "Presence of this container sets the LSP to use
      LDP signaling";

      description "LDP signaling setup for IGP-congruent LSPs";

      // include tunnel (p2p, p2mp, ...)

      uses igp-tunnel-ldp;

    }
  }

  // data definition statements

  // augment statements

  // rpc statements

  // notification statements

}
