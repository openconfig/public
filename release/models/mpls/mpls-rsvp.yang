module mpls-rsvp {

  yang-version "1";

  // namespace
  namespace "http://openconfig.net/yang/rsvp";

  prefix "rsvp";

  // import some basic types
  import ietf-inet-types { prefix inet; }
  import mpls-types { prefix mplst; }
  import ietf-yang-types { prefix yang; }
  import openconfig-types { prefix oc-types; }


  // meta
  organization "OpenConfig working group";

  contact
    "OpenConfig working group
     netopenconfig@googlegroups.com";

  description
    "Configuration for RSVP-TE signaling, including global protocol
     parameters and LSP-specific configuration for constrained-path
     LSPs";

  oc-ext:openconfig-version "0.2.0";

  revision "2015-10-14" {
    description
      "Work in progress";
    reference "0.2.0";
  }

  revision "2015-07-04" {
    description
      "Work in progress";
    reference "Pre-release";
  }

  // feature statements

  // identity statements

  // typedef statements

  // grouping statements

  grouping mpls-rsvp-soft-preemption_config {
    description "Configuration for MPLS soft preemption";
    leaf enable {
      type boolean;
      default false;
      description "Enables soft preemption on a node.";
    }

    leaf soft-preemption-timeout {
      type uint16 {
        range 0..max;
      }
      // The RFC actually recommends 30 seconds as default.
      default 0;
      description
        "Timeout value for soft preemption to revert
         to hard preemption";
      reference "RFC5712 MPLS-TE soft preemption";
    }
  }

  grouping mpls-rsvp-soft-preemption {
    description "Top level group for MPLS soft preemption";
    container soft-preemption {
      description
        "Protocol options relating to RSVP
         soft preemption";
      container config {
        description
          "Configuration parameters relating to RSVP
           soft preemption support";
        uses mpls-rsvp-soft-preemption_config;
      }
      container state {
        config false;
        description
          "State parameters relating to RSVP
           soft preemption support";
        uses mpls-rsvp-soft-preemption_config;
      }
    }
  }

  grouping mpls-rsvp-hellos_config {
    description "RSVP protocol options configuration.";

    leaf hello-interval {
      type uint16 {
        range 1000..60000;
      }
      units milliseconds;
      default 9000;
      description
        "set the interval in ms between RSVP hello
         messages";
      reference
        "RFC 3209: RSVP-TE: Extensions to RSVP for
         LSP Tunnels.
         RFC 5495: Description of the Resource
         Reservation Protocol - Traffic-Engineered
         (RSVP-TE) Graceful Restart Procedures";
    }

    leaf refresh-reduction {
      type boolean;
      default true;
      description
        "enables all RSVP refresh reduction message
         bundling, RSVP message ID, reliable message delivery
         and summary refresh";
      reference
        "RFC 2961 RSVP Refresh Overhead Reduction
         Extensions";
    }
  }

  grouping mpls-rsvp-hellos {
    description "Top level grouping for RSVP hellos parameters";
    // TODO: confirm that the described semantics are supported
    // on various implementations. Finer grain configuration
    // will be vendor-specific

    container rsvp-hellos {
      description "Top level container for RSVP hello parameters";
      container config {
        description
          "Configuration parameters relating to RSVP
           hellos";
        uses mpls-rsvp-hellos_config;
      }
      container state {
        config false;
        description "State information associated with RSVP hellos";
        uses mpls-rsvp-hellos_config;
      }
    }
  }

  grouping mpls-rsvp-subscription_config {
    description "RSVP subscription configuration";
    leaf subscription {
      type oc-types:percentage;
      description
        "percentage of the interface bandwidth that
         RSVP can reserve";
    }
  }
  grouping mpls-rsvp-subscription {
    description "Top level group for RSVP subscription options";
    container subscription {
      description
        "Bandwidth percentage reservable by RSVP
         on an interface";
      container config {
        description "TODO";
        uses mpls-rsvp-subscription_config;
      }
      container state {
        config false;
        description "TODO";
        uses mpls-rsvp-subscription_config;
      }
    }
  }

  grouping mpls-rsvp-graceful-restart_config {
    description
      "Configuration parameters relating to RSVP Graceful-Restart";

    leaf enable {
      type boolean;
      default false;
      description "Enables graceful restart on the node.";
    }

    leaf restart-time {
      type uint32;
      description
        "Graceful restart time (seconds).";
      reference
        "RFC 5495: Description of the Resource
         Reservation Protocol - Traffic-Engineered
         (RSVP-TE) Graceful Restart Procedures";
    }
    leaf recovery-time {
      type uint32;
      description
        "RSVP state recovery time";
    }
  }

  grouping mpls-rsvp-graceful-restart {
    description
      "Top level group for RSVP graceful-restart
       parameters";
    container graceful-restart {
      description "TODO";
      container config {
        description
          "Configuration parameters relating to
           graceful-restart";
        uses mpls-rsvp-graceful-restart_config;
      }
      container state {
        config false;
        description
          "State information associated with
           RSVP graceful-restart";
        uses mpls-rsvp-graceful-restart_config;
      }
    }
  }

  grouping mpls-rsvp-authentication_config {
    description "RSVP authentication parameters container.";
    leaf enable {
      type boolean;
      default false;
      description "Enables RSVP authentication on the node.";
    }
    leaf authentication-key {
      type string {
        // Juniper supports 1..16 while
        // Cisco has a much bigger range, up to 60.
        length "1..32";
      }
      description
        "authenticate RSVP signaling
         messages";
      reference
        "RFC 2747: RSVP Cryptographic Authentication";
    }
  }

  grouping mpls-rsvp-authentication {
    description
      "Top level group for RSVP authentication,
       as per RFC2747";
    container authentication {
      description "TODO";
      container config {
        description
          "Configuration parameters relating
           to authentication";
        uses mpls-rsvp-authentication_config;
      }
      container state {
        config false;
        description
          "State information associated
           with authentication";
        uses mpls-rsvp-authentication_config;
      }
    }
  }

  grouping mpls-rsvp-protection_config {
    description "RSVP facility (link/node) protection configuration";

    leaf link-protection-style-requested {
      type identityref {
	base mplst:protection-type;
      }
      description
	"style of mpls frr protection desired:
         link, link-node, or unprotected";
      default mplst:link-node-protection-requested;
    }

    leaf bypass-optimize-interval {
      type uint16;
      units seconds;
      description
        "interval between periodic optimization
         of the bypass LSPs";
      // note: this is interface specific on juniper
      // on iox, this is global. need to resolve.
    }
    // to be completed, things like enabling link protection,
    // optimization times, etc.
  }

  grouping mpls-rsvp-link-protection {
    description "Top level group for RSVP protection";
    container protection {
      description "link-protection (NHOP) related configuration";
      container config {
        description "Configuration for link-protection";
        uses mpls-rsvp-protection_config;
      }
      container state {
        config false;
        description "State for link-protection";
        uses mpls-rsvp-protection_config;
      }
    }
  }

  grouping mpls-rsvp-error-statistics {
    description "RSVP-TE packet statistics";
    container error {
      description "RSVP-TE error statistics";
      leaf authentication-failure {
        type yang:counter32;
        description
          "Authentication failure count";
      }

      leaf path-error {
        type yang:counter32;
        description
          "Path error to client count";
      }

      leaf resv-error {
        type yang:counter32;
        description
          "Resv error to client count";
      }

      leaf path-timeout {
        type yang:counter32;
        description
          "Path timeout count";
      }

      leaf resv-timeout {
        type yang:counter32;
        description
          "Resv timeout count";
      }

      leaf rate-limit {
        type yang:counter32;
        description
          "Count of packets that were rate limited";
      }

      // TODO - complete the other error statistics
    }
  }

  grouping mpls-rsvp-protocol-statistics {
    description "RSVP protocol statistics";
    container protocol {
      description "RSVP-TE protocol statistics";
      leaf hello-sent {
        type yang:counter32;
        description
          "Hello sent count";
      }

      leaf hello-rcvd {
        type yang:counter32;
        description
          "Hello received count";
      }

      leaf path-sent {
        type yang:counter32;
        description
          "Path sent count";
      }

      leaf path-rcvd {
        type yang:counter32;
        description
          "Path received count";
      }

      // TODO - To be completed the other packet statistics
    }
  }

  grouping mpls-rsvp-statistics {
    description "Top level grouping for RSVP protocol state";
    uses mpls-rsvp-protocol-state;
  }

  grouping rsvp-global {
    description "Global RSVP protocol configuration";
    container rsvp-te {
      description "RSVP-TE global signaling protocol configuration";

      container rsvp-sessions {
          description "Configuration and state of RSVP sessions";

	  container config {
            description
              "Configuration of RSVP sessions on the device";
          }

          container state {
            config false;
            description
              "State information relating to RSVP sessions
               on the device";
            uses mpls-rsvp-session-state;
          }
      }

      container rsvp-neighbors {
          description
            "Configuration and state for RSVP neighbors connecting
             to the device";

          container config {
            description "Configuration of RSVP neighbor information";
          }

          container state {
            config false;
            description
              "State information relating to RSVP neighbors";
            uses mpls-rsvp-neighbor-state;
          }
      }

      container global {
        description "Platform wide RSVP configuration and state";
        uses mpls-rsvp-graceful-restart;
        uses mpls-rsvp-soft-preemption;

        container state {
          config false;
          description "Platform wide RSVP state, including counters";
          // TODO - reconcile global and per-interface
          // protocol-related statistics

          container counters {
            config false;
            description
              "Platform wide RSVP statistics and counters";
            uses mpls-rsvp-global-protocol-state;
            uses mpls-rsvp-statistics;
          }
        }
        // interfaces, bw percentages, hello timers, etc goes here";

        list interfaces {
          key interface-name;
          description "list of per-interface RSVP configurations";

          // TODO: update to interface ref -- move to separate
          // augmentation.
          leaf interface-name {
            type string;
            description "references a configured IP interface";
          }

          uses mpls-rsvp-hellos;
          uses mpls-rsvp-authentication;
          uses mpls-rsvp-subscription;
          uses mpls-rsvp-link-protection;

          container config {
            description
              "Configuration of per-interface RSVP parameters";
          }

          container state {
            config false;
            description
              "Per-interface RSVP protocol and state information";
            uses mpls-rsvp-interfaces-state;

            container counters {
              config false;
              description
                "Interface specific RSVP statistics and counters";
              uses mpls-rsvp-protocol-state;
            }
          }
        }
      }
    }
  }

  grouping mpls-rsvp-te-tunnel {
    description
      "definitions for RSVP-signaled LSP tunnel types,
       .e.g., applicable to point-to-point LSPs";

    container tunnel {
      description
        "contains configuration stanzas for different LSP
         tunnel types (P2P, P2MP, etc.)";

      container config {
        description "configuration of overall tunnel parameters";
        uses mpls-rsvp-tunnel-type_config;
      }

      container state {
        config false;
        description "state information for mpls tunnels";
        uses mpls-rsvp-tunnel-type_config;
      }
      uses mpls-rsvp-p2p-lsp-top;
      uses mpls-rsvp-p2mp-lsp-top;
    }
  }

  grouping mpls-rsvp-p2mp-lsp-top {
    description "Top level grouping for P2MP LSPs";
    container p2mp-lsp {
      when "tunnel-type = 'P2MP'" {
        description
          "container is active when LSP tunnel type is
           point to multipoint";
      }
      description "properties of point-to-multipoint tunnels";
      container config {
        description "configuration of p2mp lsps";
        uses mpls-rsvp-tunnel-rsvp-p2mp_config;
      }
      container state {
        config false;
        description "state information of p2mp lsps";
        uses mpls-rsvp-tunnel-rsvp-p2mp_config;
      }
    }
  }

  grouping mpls-rsvp-p2p-lsp-top {
    description "Top level grouping for P2P LSPs";
    container p2p-lsp {
      when "tunnel-type = 'P2P'" {
        description
          "container active when LSP tunnel type is
           point to point";
      }
      description "properties of point-to-point tunnels";
      container config {
        description "configuration for p2p lsps";
        uses mpls-rsvp-tunnel-rsvp-p2p_config;
      }
      container state {
        config false;
        description "state information for p2p lsps";
        uses mpls-rsvp-tunnel-rsvp-p2p_config;
      }
    }
  }

  grouping mpls-rsvp-tunnel-type_config {
    description "Configuration of MPLS tunnel type";
    leaf tunnel-type {
      type mplst:tunnel-type;
      description "specifies the type of LSP, e.g., P2P or P2MP";
    }
  }

  grouping mpls-rsvp-tunnel-rsvp-p2mp_config {
    description "properties of point-to-multipoint tunnels";
    leaf-list destination {
      type inet:ip-address;
      description
        "list of destinations / egress nodes for the
         multipoint LSP tunnel";
    }

  }

  grouping mpls-rsvp-tunnel-rsvp-p2p_config {
    description "properties of point-to-point tunnels";
    leaf setup-priority {
      type uint8 {
        range 0..7;
      }
      default 7;
      description
        "preemption priority during LSP setup, lower is
         higher priority; default 7 indicates that LSP will not
         preempt established LSPs during setup";
      reference "RFC 3209 - RSVP-TE: Extensions to RSVP for
        LSP Tunnels";
    }

    leaf hold-priority {
      type uint8 {
        range 0..7;
      }
      default 0;
      description
        "preemption priority once the LSP is established,
         lower is higher priority; default 0 indicates other LSPs
         will not preempt the LSPs once established";
      reference "RFC 3209 - RSVP-TE: Extensions to RSVP for
        LSP Tunnels";
    }

    leaf retry-timer {
      type uint16 {
        range 1..600;
      }
      units seconds;
      description
        "sets the time between attempts to establish the
         LSP";
    }
    leaf destination {
      type inet:ip-address;
      description "destination egress node for the LSP";
    }

    leaf tunnel-local-id {
      type union {
        type uint32;
        type string;
      }
      description
        "locally signficant optional identifier for the
         LSP; may be a numerical or string value";
    }

    leaf soft-preemption {
      type boolean;
      default false;
      description "enables RSVP soft-preemption on this LSP";
    }
  }

  grouping te-lsp-rsvp-setup {
    description "data definitions for RSVP-signalled LSPs";
    container rsvp {
      presence
        "Presence of this container sets the LSP to use
         RSVP signaling";
      description "Configuration for RSVP-signalled TE LSPs";
      container path-specification {
        description
          "Definition of primary/backup paths for purpose
           of signaling the LSP";
      }
      uses mpls-rsvp-te-tunnel;
    }
  }

  grouping mpls-rsvp-neighbor-state {
    description "State information for RSVP neighbors";

    list rsvp-neighbors {
      key "neighbor-address";
      description
        "List of RSVP neighbors connecting to the device,
        keyed by neighbor address";

      leaf neighbor-address {
        type inet:ip-address;
        description "Address of RSVP neighbor";
      }

      leaf detected-interface {
        type string;
        description "Interface where RSVP neighbor was detected";
      }

      leaf neighbor-status {
        type enumeration {
          enum UP {
            description
              "RSVP hello messages are detected from the neighbor";
          }
          enum DOWN {
            description
              "RSVP neighbor not detected as up, due to a
               communication failure or IGP notification
               the neighbor is unavailable";
          }
        }
        description "Enumuration of possible RSVP neighbor states";
      }

      leaf neighbor-refresh-reduction {
        type boolean;
        description
          "Suppport of neighbor for RSVP refresh reduction";
        reference
          "RFC 2961 RSVP Refresh Overhead Reduction
           Extensions";
      }
    }
  }

  grouping mpls-rsvp-session-state {
    description "State information for RSVP TE sessions";
    list rsvp-te-sessions {
      key "source-port destination-port
       source-address destination-address";
      description "List of RSVP sessions";

      leaf source-address {
        type inet:ip-address;
        description "Origin address of RSVP session";
      }

      leaf destination-address {
        type inet:ip-address;
        description "Destination address of RSVP session";
      }

      leaf source-port {
        type uint16;
        description "RSVP source port";
        reference "RFC 2205";
      }

      leaf destination-port {
        type uint16;
        description "RSVP source port";
        reference "RFC 2205";

      }

      leaf session-state {
        type enumeration {
          enum UP {
            description "RSVP session is up";
          }
          enum DOWN {
            description "RSVP session is down";
          }
        }
        description "Enumeration of RSVP session states";
      }

      leaf session-type {
        type enumeration {
          enum SOURCE {
            description "RSVP session originates on this device";
          }
          enum TRANSIT {
            description "RSVP session transits this device only";
          }
          enum DESTINATION {
            description "RSVP session terminates on this device";
          }
        }
        description "Enumeration of possible RSVP session types";
      }

      leaf tunnel-id {
        type uint16;
        description "Unique identifier of RSVP session";
      }

      leaf label-in {
        type mplst:mpls-label;
        description
          "Incoming MPLS label associated with this RSVP session";
      }

      leaf label-out {
        type mplst:mpls-label;
        description
          "Outgoing MPLS label associated with this RSVP session";
      }

      leaf-list associated-lsps {
        type leafref {
          path "/mpls/lsps/constrained-path/label-switched-path/" +
          "config/signaled-name";
        }
        description
          "List of label switched paths associated with this RSVP
           session";
      }
    }
  } //rsvp-session-state

  grouping mpls-rsvp-interfaces-state {
    description "RSVP state information relevant to an interface";
    leaf available-bandwidth {
      type uint64;
      description "Bandwidth currently available";
    }

    leaf reserved-bandwidth {
      type uint64;
      description "Bandwidth currently reserved";
    }

    leaf highwater-mark {
      type uint64;
      description "Maximum bandwidth ever reserved";
    }

    leaf active-reservation-count {
      type yang:gauge64;
      description "Number of active RSVP reservations";
    }
  }

  grouping mpls-rsvp-global-protocol-state {
    description "RSVP protocol statistics which may not apply
      on an interface, but are significant globally.";

    leaf path-timeouts {
      type yang:counter64;
      description "TODO";
    }

    leaf reservation-timeouts {
      type yang:counter64;
      description "TODO";
    }

    leaf rate-limited-messages {
      type yang:counter64;
      description "RSVP messages dropped due to rate limiting";
    }
  }

  grouping mpls-rsvp-protocol-state {
    description "RSVP protocol statistics and message counters";
    leaf in-path-messages {
      type yang:counter64;
      description "Number of received RSVP Path messages";
    }

    leaf in-path-error-messages {
      type yang:counter64;
      description "Number of received RSVP Path Error messages";
    }

    leaf in-path-tear-messages {
      type yang:counter64;
      description "Number of received RSVP Path Tear messages";
    }

    leaf in-reservation-messages {
      type yang:counter64;
      description "Number of received RSVP Resv messages";
    }

    leaf in-reservation-error-messages {
      type yang:counter64;
      description "Number of received RSVP Resv Error messages";
    }

    leaf in-reservation-tear-messages {
      type yang:counter64;
      description "Number of received RSVP Resv Tear messages";
    }

    leaf in-rsvp-hello-messages {
      type yang:counter64;
      description "Number of received RSVP hello messages";
    }

    leaf in-rsvp-srefresh-messages {
      type yang:counter64;
      description "Number of received RSVP summary refresh messages";
    }

    leaf in-rsvp-ack-messages {
      type yang:counter64;
      description
        "Number of received RSVP refresh reduction ack
         messages";
    }

    leaf out-path-messages {
      type yang:counter64;
      description "Number of sent RSVP PATH messages";
    }

    leaf out-path-error-messages {
      type yang:counter64;
      description "Number of sent RSVP Path Error messages";
    }

    leaf out-path-tear-messages {
      type yang:counter64;
      description "Number of sent RSVP Path Tear messages";
    }

    leaf out-reservation-messages {
      type yang:counter64;
      description "Number of sent RSVP Resv messages";
    }

    leaf out-reservation-error-messages {
      type yang:counter64;
      description "Number of sent RSVP Resv Error messages";
    }

    leaf out-reservation-tear-messages {
      type yang:counter64;
      description "Number of sent RSVP Resv Tear messages";
    }

    leaf out-rsvp-hello-messages {
      type yang:counter64;
      description "Number of sent RSVP hello messages";
    }

    leaf out-rsvp-srefresh-messages {
      type yang:counter64;
      description "Number of sent RSVP summary refresh messages";
    }

    leaf out-rsvp-ack-messages {
      type yang:counter64;
      description
        "Number of sent RSVP refresh reduction ack messages";
    }
  }



  // data definition statements

  // augment statements

  // rpc statements

  // notification statements

}
