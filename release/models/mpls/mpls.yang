module mpls {

  yang-version "1";

  // namespace
  namespace "http://openconfig.net/yang/mpls";

  prefix "mpls";


  // import some basic types
  import mpls-types { prefix mplst; }
  import mpls-rsvp { prefix rsvp; }
  import mpls-sr { prefix sr; }
  import mpls-ldp { prefix ldp; }
  import openconfig-types { prefix oc-types; }
  import openconfig-interfaces { prefix ocif; }

  // include submodules
  include mpls-te;
  include mpls-igp;
  include mpls-static;


  // meta
  organization "OpenConfig working group";

  contact
    "OpenConfig working group
    netopenconfig@googlegroups.com";

  description
    "This module provides data definitions for configuration of
    Multiprotocol Label Switching (MPLS) and associated protocols for
    signaling and traffic engineering.

    RFC 3031: Multiprotocol Label Switching Architecture

    The MPLS / TE data model consists of several modules and
    submodules as shown below.  The top-level MPLS module describes
    the overall framework.  Three types of LSPs are supported:

    i) traffic-engineered (or constrained-path)

    ii) IGP-congruent (LSPs that follow the IGP path)

    iii) static LSPs which are not signaled

    The structure of each of these LSP configurations is defined in
    corresponding submodules.  Companion modules define the relevant
    configuration and operational data specific to key signaling
    protocols used in operational practice.


                              +-------+
            +---------------->| MPLS  |<--------------+
            |                 +-------+               |
            |                     ^                   |
            |                     |                   |
       +----+-----+      +--------+-------+     +-----+-----+
       | TE LSPs  |      | IGP-based LSPs |     |static LSPs|
       |          |      |                |     |           |
       +----------+      +----------------+     +-----------+
           ^  ^                    ^  ^
           |  +----------------+   |  +--------+
           |                   |   |           |
           |   +------+      +-+---+-+      +--+--+
           +---+ RSVP |      |SEGMENT|      | LDP |
               +------+      |ROUTING|      +-----+
                             +-------+
    ";

  oc-ext:openconfig-version "0.2.0";

  revision "2015-10-14" {
    description
      "Work in progress";
    reference "0.2.0";
  }

  revision "2015-07-04" {
    description
      "Work in progress";
    reference "Pre-release";
  }

  // feature statements

  // identity statements


  // grouping statements

  grouping path-setup-common {
    description "common definitions for all signaling protocols";

    // TODO: not clear we really need this
    leaf path-setup-type {
      type identityref {
        base mplst:path-setup-protocol;
      }
      description "path setup protocol to use with the LSP";
    }
  }

  grouping mpls-admin-group_config {
    description
      "configuration data for MPLS link admin groups";

      leaf admin-group-name {
        type string;
        description "name for mpls admin-group";
      }

      leaf admin-group-value {
        type uint32;
        description "value for mpls admin-group";
      }

  }


 grouping mpls-admin-groups-top {

   description "top-level mpls admin-groups config
   and state containers";

    container mpls-admin-groups {
      description
        "Top-level container for admin-groups configuration
        and state";

      list admin-group {
	key admin-group-name;
	description "configuration of value to name mapping
        for mpls affinities/admin-groups";

	leaf admin-group-name {
	   type leafref {
            path "../mpls:config/mpls:admin-group-name";
          }
          description
            "name for mpls admin-group";
	}
	container config {
	  description "Configurable items for admin-groups";
	  uses mpls-admin-group_config;
	}

	container state {
	  description "Operational state for admin-groups";
	  uses mpls-admin-group_config;
	}
      }
    }
 }


  grouping mpls-te-igp-flooding-bandwidth_config {
    description
      "Configurable items for igp flooding bandwidth
       threshold configuration.";
    leaf threshold-type {
      type enumeration {
	enum DELTA {
	  description "DELTA indicates that the local
          system should flood IGP updates when a
          change in reserved bandwidth >= the specified
          delta occurs on the interface.";
	}
	enum THRESHOLD-CROSSED {
	  description "THRESHOLD-CROSSED indicates that
          the local system should trigger an update (and
          hence flood) the reserved bandwidth when the
          reserved bandwidth changes such that it crosses,
          or becomes equal to one of the threshold values.";
	}
      }
      description
	"The type of threshold that should be used to specify the
      values at which bandwidth is flooded. DELTA indicates that the
      local system should flood IGP updates when a change in reserved
      bandwidth >= the specified delta occurs on the interface. Where
      THRESHOLD-CROSSED is specified, the local system should trigger
      an update (and hence flood) the reserved bandwidth when the
      reserved bandwidth changes such that it crosses, or becomes
      equal to one of the threshold values";
    }

    leaf delta-percentage {
      when "../threshold-type = 'DELTA'" {
        description
          "The percentage delta can only be specified when the
          threshold type is specified to be a percentage delta of
          the reserved bandwidth";
      }
      type oc-types:percentage;
      description
	"The percentage of the maximum-reservable-bandwidth considered
      as the delta that results in an IGP update being flooded";
    }

    leaf threshold-specification {
      when "../threshold-type = 'THRESHOLD-CROSSED'" {
        description
          "The selection of whether mirrored or separate threshold
          values are to be used requires user specified thresholds to
          be set";
      }
      type enumeration {
      	enum MIRRORED-UP-DOWN {
      	  description
            "MIRRORED-UP-DOWN indicates that a single set of
            threshold values should be used for both increasing
            and decreasing bandwidth when determining whether
            to trigger updated bandwidth values to be flooded
            in the IGP TE extensions.";
      	}
      	enum SEPARATE-UP-DOWN {
      	  description
            "SEPARATE-UP-DOWN indicates that a separate
            threshold values should be used for the increasing
            and decreasing bandwidth when determining whether
            to trigger updated bandwidth values to be flooded
            in the IGP TE extensions.";
      	}
      }
      description

        "This value specifies whether a single set of threshold
        values should be used for both increasing and decreasing
        bandwidth when determining whether to trigger updated
        bandwidth values to be flooded in the IGP TE extensions.
        MIRRORED-UP-DOWN indicates that a single value (or set of
        values) should be used for both increasing and decreasing
        values, where SEPARATE-UP-DOWN specifies that the increasing
        and decreasing values will be separately specified";
    }

    leaf-list up-thresholds {
      when "../threshold-type = 'THRESHOLD-CROSSED'" +
        "and ../threshold-specification = 'SEPARATE-UP-DOWN'" {
        description
          "A list of up-thresholds can only be specified when the
          bandwidth update is triggered based on crossing a threshold
          and separate up and down thresholds are required";
      }
      type oc-types:percentage;
      description
        "The thresholds (expressed as a percentage of the maximum
        reservable bandwidth) at which bandwidth updates are to be
        triggered when the bandwidth is increasing.";
    }

    leaf-list down-thresholds {
      when "../threshold-type = 'THRESHOLD-CROSSED'" +
        "and ../threshold-specification = 'SEPARATE-UP-DOWN'" {
        description
          "A list of down-thresholds can only be specified when the
          bandwidth update is triggered based on crossing a threshold
          and separate up and down thresholds are required";
      }
      type oc-types:percentage;
      description
        "The thresholds (expressed as a percentage of the maximum
        reservable bandwidth) at which bandwidth updates are to be
        triggered when the bandwidth is decreasing.";
    }

    leaf-list up-down-thresholds {
      when "../threshold-type = 'THRESHOLD-CROSSED'" +
        "and ../threshold-specification = 'MIRRORED-UP-DOWN'" {
        description
          "A list of thresholds corresponding to both increasing
          and decreasing bandwidths can be specified only when an
          update is triggered based on crossing a threshold, and
          the same up and down thresholds are required.";
      }
      type oc-types:percentage;
      description
        "The thresholds (expressed as a percentage of the maximum
        reservable bandwidth of the interface) at which bandwidth
        updates are flooded - used both when the bandwidth is
        increasing and decreasing";
    }
  }

  grouping mpls-te-igp-flooding-bandwdith-if {
    description "Interface-level group for traffic engineering
    database flooding options options";

     container igp-flooding-bandwidth {
      description "Interface bandwidth change percentages
      that trigger update events into the IGP traffic
      engineering database (TED)";
      uses  mpls-te-igp-flooding-bandwidth_config;
     }
  }


  grouping  mpls-te-igp-flooding-bandwidth {
    description "Top level group for traffic engineering
    database flooding options";
    container igp-flooding-bandwidth {
      description "Interface bandwidth change percentages
      that trigger update events into the IGP traffic
      engineering database (TED)";
      container config {
        description "Configuration parameters for TED
        update threshold ";
        uses  mpls-te-igp-flooding-bandwidth_config;
      }
      container state {
	config false;
	description "State parameters for TED update threshold ";
	uses  mpls-te-igp-flooding-bandwidth_config;
      }
    }
  }


  grouping te_lsp_delay_config {
    description "Group for the timers goerning the delay
    in installation and cleanup of TE LSPs";

    leaf te-lsp-install-delay {
      type uint16 {
        range 0..3600;
      }
      units seconds;
      description "delay the use of newly installed te lsp for a
      specified amount of time.";
    }

    leaf te-lsp-cleanup-delay {
      type uint16;
      units seconds;
      description "delay the removal of old te lsp for a specified
      amount of time";
    }
  }

  grouping te-interface-attributes-top {
    description
      "Top level grouping for attributes
       for TE interfaces.";

      list interface {
	key interface-name;
	description "List of TE interfaces";

	leaf interface-name {
	  type leafref {
	    path "../config/interface-name";
	    require-instance true;
	  }
	  description "The interface name";
	}

	container config {
	  description "Configuration parameters related to TE interfaces:";
          uses te-interface-attributes-config;
	}

	container state {
	  config false;
	  description "State parameters related to TE interfaces";
	  uses te-interface-attributes-config;
	}
      }
  }

  grouping te-interface-attributes-config {
    description "global level definitions for interfaces
    on which TE is run";

      leaf interface-name {
        type ocif:interface-ref;
        description "reference to interface name";
      }

      leaf te-metric {
	type uint32;
	description "TE specific metric for the link";
      }

      list srlg {
	key srlg-name;
	description "list of shared risk link groups on the
        interface";
	leaf srlg-name {
	  type string;
	  description "The SRLG group identifier";
	}
      }

      list admin-group {
	key admin-group-name;
	description "list of admin groups on the
        interface";
	leaf admin-group-name {
	  type string;
	  description "The admin group identifier";
	}
      }

      uses  mpls-te-igp-flooding-bandwdith-if;

  }

  grouping mpls-te-lsp-timers {
    description
      "Grouping for traffic engineering timers";
    container te_lsp_timers {
      description
      "definition for delays associated with setup
      and cleanup of TE LSPs";

      container config {
        description
        "Configuration parameters related
        to timers for TE LSPs";

        uses te_lsp_delay_config;
        uses te_lsp_reoptimize_config;
      }
      container state {
        config false;
        description "State related to timers for TE LSPs";

        uses te_lsp_delay_config;
        uses te_lsp_reoptimize_config;
      }
    }
  }

container mpls {
    presence "top-level container for MPLS config and operational
    state";

    description "Anchor point for mpls configuration and operational
    data";

    container global {
      // entropy label support, label ranges will be added here.
     description "general mpls configuration applicable to any
     type of LSP and signaling protocol - label ranges,
     entropy label supportmay be added here";
    }

    container te-global-attributes {
      description "traffic-engineering global attributes";
      uses mpls-te-srlg-top;
      uses mpls-te-igp-flooding-bandwidth;
      uses mpls-admin-groups-top;
      uses mpls-te-lsp-timers;

    }

    container te-intf-attributes {
      description "traffic engineering attributes specific
      for interfaces";
      uses te-interface-attributes-top;
    }

    container signaling-protocols {
      description "top-level signaling protocol configuration";

      uses rsvp:rsvp-global;
      uses sr:sr-global;
      uses ldp:ldp-global;
    }

    container lsps {
      description "LSP definitions and configuration";

      container constrained-path {
        description "traffic-engineered LSPs supporting different
        path computation and signaling methods";

        uses mpls-te-global;
        uses path-definitions;

        list label-switched-path {
          key signaled-name;
          description "list of defined TE LSPs";
          leaf signaled-name {
            type leafref {
              path "../config/signaled-name";
            }
            description "LSP name, also carried in signaling messages
            when appropriate";
          }
          uses te-lsp-common;
          uses te-lsp-setup;
        }
      }

      container unconstrained-path {
        description "LSPs that use the IGP-determined path, i.e., non
        traffic-engineered, or non constrained-path";

        uses igp-lsp-common;
        uses igp-lsp-setup;

      }

      container static-lsps {
      description "statically configured LSPs, without dynamic
      signaling";

        uses static-lsp-main;
      }
    }
  }

  // augment statements

  // rpc statements

  // notification statements
  }
