module mpls-types {

  yang-version "1";

  // namespace
  namespace "http://openconfig.net/yang/mpls-types";

  prefix "mplst";


  // meta
  organization "OpenConfig working group";

  contact
    "OpenConfig working group
    netopenconfig@googlegroups.com";

  description
    "General types for MPLS / TE data model";

  oc-ext:openconfig-version "0.2.0";

  revision "2015-10-14" {
    description
      "Work in progress";
    reference "0.2.0";
  }

  revision "2015-07-04" {
    description
      "Work in progress";
    reference "Pre-release";
  }

  // feature statements

  // identity statements

  // using identities rather than enum types to simplify adding new
  // signaling protocols as they are introduced and supported
  identity path-setup-protocol {
    description "base identity for supported MPLS signaling
    protocols";
  }

  identity path-setup-rsvp {
    base path-setup-protocol;
    description "RSVP-TE signaling protocol";
  }

  identity path-setup-sr {
    base path-setup-protocol;
    description "Segment routing";
  }

  identity path-setup-ldp {
    base path-setup-protocol;
    description "lDP - RFC 5036";
  }


  identity protection-type {
    description "base identity for protection type";
  }

  identity unprotected {
    base protection-type;
    description "no protection is desired";
  }

  identity link-protection-requested {
    base protection-type;
    description "link protection is desired";
  }

  identity link-node-protection-requested {
    base protection-type;
    description "node and link protection are both desired";
  }

  identity lsp-type {
    description
      "Base identity for describing the type of
       label switched path";
  }

  identity INGRESS {
    base "lsp-type";
    description
      "Label switched path is an ingress (headend)
       LSP";
  }

  identity EGRESS {
    base "lsp-type";
    description
      "Label switched path is an egress (tailend)
       LSP";
  }

  identity TRANSIT {
    base "lsp-type";
    description
      "Label switched path is a transit LSP";
  }

  identity lsp-oper-status {
    description
      "Base identity for LSP operational status";
  }

  identity DOWN {
    base "lsp-oper-status";
    description
      "LSP is operationally down or out of service";
  }

  identity UP {
    base "lsp-oper-status";
    description
      "LSP is operationally active and available
       for traffic.";
  }

  // typedef statements
  typedef mpls-label {
    type union {
      type uint32 {
        range 16..1048575;
      }
      type enumeration {
        enum IPV4_EXPLICIT_NULL {
          value 0;
          description "valid at the bottom of the label stack,
          indicates that stack must be popped and packet forwarded
          based on IPv4 header";
        }
        enum ROUTER_ALERT {
          value 1;
          description "allowed anywhere in the label stack except
          the bottom, local router delivers packet to the local CPU
          when this label is at the top of the stack";
        }
        enum IPV6_EXPLICIT_NULL {
          value 2;
          description "valid at the bottom of the label stack,
          indicates that stack must be popped and packet forwarded
          based on IPv6 header";
        }
        enum IMPLICIT_NULL {
          value 3;
          description "assigned by local LSR but not carried in
          packets";
        }
        enum ENTROPY_LABEL_INDICATOR {
          value 7;
          description "Entropy label indicator, to allow an LSR
          to distinguish between entropy label and applicaiton
          labels RFC 6790";
        }
      }
    }
    description "type for MPLS label value encoding";
    reference "RFC 3032 - MPLS Label Stack Encoding";
  }

  typedef tunnel-type {
    type enumeration {
      enum P2P {
        description "point-to-point label-switched-path";
      }
      enum P2MP {
        description "point-to-multipoint label-switched-path";
      }
      enum MP2MP {
        description "multipoint-to-multipoint label-switched-path";
      }
    }
    description "defines the tunnel type for the LSP";
    reference
      "RFC 6388 - Label Distribution Protocol Extensions for
      Point-to-Multipoint and Multipoint-to-Multipoint Label Switched
      Paths
      RFC 4875 - Extensions to  Resource Reservation Protocol
      - Traffic Engineering (RSVP-TE) for Point-to-Multipoint TE
      Label Switched Paths (LSPs)";
  }





  // grouping statements

  // data definition statements

  // augment statements

  // rpc statements

  // notification statements

}
