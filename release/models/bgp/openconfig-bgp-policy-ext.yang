module openconfig-bgp-policy-ext {

  yang-version "1";

  // namespace
  namespace "http://openconfig.net/yang/bgp-policy/extension";

  prefix "oc-bgp-pol-ext";

  import openconfig-inet-types { prefix oc-inet; }
  import openconfig-routing-policy {prefix oc-rpol; }
  import openconfig-bgp-types { prefix oc-bgp-types; }
  import openconfig-bgp-policy { prefix oc-bgp-pol; }
  import openconfig-extensions { prefix oc-ext; }
  import openconfig-routing-policy-ext {prefix oc-rpol-ext;}

  organization
      "OpenConfig Working Group";

  contact
      "OpenConfig Working Group
      www.openconfig.net";

  description
    "This module describes a deviation for BGP routing policy 
     configuration extensions.";

  oc-ext:openconfig-version "0.1.1";

  revision "2020-08-01" {
    description
      "Added the action for as-path, community and ext-community.";
    reference "0.1.2";
  }

  revision "2020-04-08" {
    description
      "Added the attributes for IPv6 next hop.";
    reference "0.1.1";
  }

  revision "2019-11-13" {
    description
      "BGP Routing Policy extensions.";
    reference "0.1.0";
  }

  grouping bgp-policy-ext-action-next-hop-set-config {
    description
        "Configuration data for IP nexthop under BGP policy conditions";
      leaf next-hop-set {
          type leafref {
              path "/oc-rpol:routing-policy/oc-rpol:defined-sets/oc-rpol:prefix-sets/oc-rpol:prefix-set/oc-rpol:config/oc-rpol:name";
          }
          description "References a defined prefix set";
      }
  }

  typedef bgp-community-defined-regexp-type {
      type string;
      description
          "Type definition for communities specified as regular
          expression patterns";
    }
 
  grouping bgp-policy-ext-ipv6-next-hop-config {
    description
        "Configuration data for IPv6 nexthop under BGP policy actions";
      leaf set-ipv6-next-hop-global {
          type oc-inet:ipv6-address;
          description "set the IPv6 global next-hop attribute in the route update";
      }

      leaf set-ipv6-next-hop-prefer-global {
          type boolean;
          description
              "If we receive a ipv6 global and link-local address for the route, 
              then prefer to use the global address as the nexthop.";
      }
  }

  deviation /oc-rpol:routing-policy/oc-rpol:defined-sets/oc-bgp-pol:bgp-defined-sets/oc-bgp-pol:community-sets/oc-bgp-pol:community-set/oc-bgp-pol:config/oc-bgp-pol:community-member {
      deviate replace {
          type union {
              type oc-bgp-types:bgp-std-community-type;
              type bgp-community-defined-regexp-type;
              type oc-bgp-types:bgp-well-known-community-type;
          }
      }
  }

  deviation /oc-rpol:routing-policy/oc-rpol:defined-sets/oc-bgp-pol:bgp-defined-sets/oc-bgp-pol:ext-community-sets/oc-bgp-pol:ext-community-set/oc-bgp-pol:config/oc-bgp-pol:ext-community-member {
      deviate replace {
          type union {
              type oc-bgp-types:bgp-ext-community-type;
              type bgp-community-defined-regexp-type;
          }
      }
  }

  augment /oc-rpol:routing-policy/oc-rpol:policy-definitions/oc-rpol:policy-definition/oc-rpol:statements/oc-rpol:statement/oc-rpol:conditions/oc-bgp-pol:bgp-conditions/oc-bgp-pol:config {
    description
        "Policy definition extensions for BGP conditions";
      uses bgp-policy-ext-action-next-hop-set-config;
  }

  augment /oc-rpol:routing-policy/oc-rpol:policy-definitions/oc-rpol:policy-definition/oc-rpol:statements/oc-rpol:statement/oc-rpol:conditions/oc-bgp-pol:bgp-conditions/oc-bgp-pol:state {
    description
        "Policy definition extensions for BGP conditions";
      uses bgp-policy-ext-action-next-hop-set-config;
  }

  augment /oc-rpol:routing-policy/oc-rpol:policy-definitions/oc-rpol:policy-definition/oc-rpol:statements/oc-rpol:statement/oc-rpol:actions/oc-bgp-pol:bgp-actions/oc-bgp-pol:config {
    description
        "Policy definition extensions for BGP actions";
        uses bgp-policy-ext-ipv6-next-hop-config;
  }

  augment /oc-rpol:routing-policy/oc-rpol:policy-definitions/oc-rpol:policy-definition/oc-rpol:statements/oc-rpol:statement/oc-rpol:actions/oc-bgp-pol:bgp-actions/oc-bgp-pol:state {
    description
        "Policy definition extensions for BGP actions";
        uses bgp-policy-ext-ipv6-next-hop-config;
  }

  augment /oc-rpol:routing-policy/oc-rpol:defined-sets/oc-bgp-pol:bgp-defined-sets/oc-bgp-pol:as-path-sets/oc-bgp-pol:as-path-set/oc-bgp-pol:config {
    description
        "BGP as-path set extensions";
      uses oc-rpol-ext:routing-policy-ext-action-config;
  }

  augment /oc-rpol:routing-policy/oc-rpol:defined-sets/oc-bgp-pol:bgp-defined-sets/oc-bgp-pol:as-path-sets/oc-bgp-pol:as-path-set/oc-bgp-pol:state {
    description
        "BGP as-path set extensions";
      uses oc-rpol-ext:routing-policy-ext-action-config;
  }

  augment /oc-rpol:routing-policy/oc-rpol:defined-sets/oc-bgp-pol:bgp-defined-sets/oc-bgp-pol:community-sets/oc-bgp-pol:community-set/oc-bgp-pol:config {
    description
        "BGP community set extensions";
      uses oc-rpol-ext:routing-policy-ext-action-config;
  }

  augment /oc-rpol:routing-policy/oc-rpol:defined-sets/oc-bgp-pol:bgp-defined-sets/oc-bgp-pol:community-sets/oc-bgp-pol:community-set/oc-bgp-pol:state {
    description
        "BGP community set extensions";
      uses oc-rpol-ext:routing-policy-ext-action-config;
  }

  augment /oc-rpol:routing-policy/oc-rpol:defined-sets/oc-bgp-pol:bgp-defined-sets/oc-bgp-pol:ext-community-sets/oc-bgp-pol:ext-community-set/oc-bgp-pol:config {
    description
        "BGP ext-community set extensions";
      uses oc-rpol-ext:routing-policy-ext-action-config;
  }

  augment /oc-rpol:routing-policy/oc-rpol:defined-sets/oc-bgp-pol:bgp-defined-sets/oc-bgp-pol:ext-community-sets/oc-bgp-pol:ext-community-set/oc-bgp-pol:state {
    description
        "BGP ext-community set extensions";
      uses oc-rpol-ext:routing-policy-ext-action-config;
  }

  // rpc statements

  // notification statements
}
