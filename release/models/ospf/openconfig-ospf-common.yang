submodule openconfig-ospf-common {

  belongs-to openconfig-ospf {
    prefix "oc-ospf";
  }

  import openconfig-extensions { prefix "oc-ext"; }

  // meta
  organization "OpenConfig working group";

  contact
    "OpenConfig working group
    www.openconfig.net";

  description
    "This submodule provides common OSPF configuration and operational
    state parameters that are shared across multiple contexts";

  oc-ext:openconfig-version "0.7.0";

  revision "2026-09-11" {
    description
      "Add minimum-hold leaf to OSPF global timers, equivalent to
      spf-second-interval and lsp-second-wait-interval of IS-IS
      global timers.";
    reference "0.7.0";
  }
  revision "2026-09-10" {
    description
      "Add send-default-route container to the OSPF global structure,
      allowing origination of a default external route, equivalent to
      send-default-route of BGP global and neighbors config.";
    reference "0.6.0";
  }
  revision "2026-09-09" {
    description
      "Add nsr container to OSPF global structure, equivalent to
      that of ISIS global config.";
    reference "0.5.0";
  }
  revision "2026-09-08" {
    description
      "Add max-ecmp-paths leaf to OSPF global config, equivalent to
      that of ISIS global config.";
    reference "0.4.0";
  }
  revision "2026-09-07" {
    description
      "Add reference-bandwidth container to OSPF global structure,
      equivalent to that of ISIS global config.";
    reference "0.3.0";
  }
  revision "2026-09-06" {
    description
      "Add route-preference container to OSPF global structure,
      providing administrative distance (preference) leafs for
      intra-area, inter-area and external OSPF routes, equivalent to
      those of ISIS global config.";
    reference "0.2.0";
  }
  revision "2025-08-10" {
    description
      "Removed duplicate import and updated prefixes in openconfig-ospf-area";
    reference "0.1.1";
  }
  revision "2025-02-13" {
    description
      "Initial revision";
    reference "0.0.1";
  }

  grouping ospf-common-timers {
    description
      "Common definition of the type of timers that the OSPF implementation
      uses";

    leaf timer-type {
      type enumeration {
        enum LINEAR_BACKOFF {
          description
            "The backoff used by the OSPF implementation is linear, such that
            a common delay is added following each event.";
        }
        enum EXPONENTIAL_BACKOFF {
          description
            "The backoff used by the OSPF implementation is exponential, such
            that the delay added following each event increases.";
        }
      }
      description
        "The timer mode that is utilised by the implementation.";
    }
  }

}
