module openconfig-ospf {

  yang-version "1";

  // namespace
  namespace "http://openconfig.net/yang/ospf";

  prefix "oc-ospf";

  import openconfig-extensions { prefix "oc-ext"; }

  // Include submodules.
  include openconfig-ospf-global;
  include openconfig-ospf-area;
  include openconfig-ospf-area-interface;
  include openconfig-ospf-common;


  // meta
  organization "OpenConfig working group";

  contact
    "OpenConfig working group
    www.openconfig.net";

  description
    "This module provides common OSPF configuration and operational
    state parameters that are shared across multiple contexts";

  oc-ext:openconfig-version "0.7.0";

  revision "2026-09-11" {
    description
      "Add minimum-hold leaf to OSPF global timers, equivalent to
      spf-second-interval and lsp-second-wait-interval of IS-IS
      global timers.";
    reference "0.7.0";
  }
  revision "2026-09-10" {
    description
      "Add send-default-route container to the OSPF global
      structure, allowing origination of a default external route,
      equivalent to send-default-route of BGP global and neighbors
      config.";
    reference "0.6.0";
  }
  revision "2026-09-09" {
    description
      "Add nsr container to OSPF global structure, equivalent to
      that of ISIS global config.";
    reference "0.5.0";
  }
  revision "2026-09-08" {
    description
      "Add max-ecmp-paths leaf to OSPF global config, equivalent to
      that of ISIS global config.";
    reference "0.4.0";
  }
  revision "2026-09-07" {
    description
      "Add reference-bandwidth container to OSPF global structure,
      equivalent to that of ISIS global config.";
    reference "0.3.0";
  }
  revision "2026-09-06" {
    description
      "Add route-preference container to OSPF global structure,
      providing administrative distance (preference) leafs for
      intra-area, inter-area and external OSPF routes, equivalent to
      those of ISIS global config.";
    reference "0.2.0";
  }
  revision "2025-08-10" {
    description
      "Removed duplicate import and updated prefixes in openconfig-ospf-area";
    reference "0.1.1";
  }
  revision "2025-02-13" {
    description
      "Initial revision";
    reference "0.0.1";
  }


  grouping ospfv3-top {
    description
      "Top-level OSPFv3 configuration and operational state";



    container ospfv3 {
      description
        "Top-level configuration and operational state for
        Open Shortest Path First (OSPF) v3";



      uses ospf-global-structural;



      container areas {
        description
          "Configuration and operational state relating to an
          OSPFv3 area.";



        list area {
          key "identifier";



          description
            "The OSPFv3 areas within which the local system exists";



          leaf identifier {
            type leafref {
              path "../config/identifier";
            }
            description
              "A reference to the identifier for the area.";
          }



          uses ospf-area-structure;
        }
      }
    }
  }

}
