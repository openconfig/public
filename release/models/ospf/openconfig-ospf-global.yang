submodule openconfig-ospf-global {

  belongs-to openconfig-ospf {
    prefix "oc-ospf";
  }

  import ietf-yang-types { prefix "yang"; }
  import openconfig-extensions { prefix "oc-ext"; }
  import openconfig-routing-policy { prefix "oc-rpol"; }
  import openconfig-ospf-types { prefix "oc-ospft"; }

  // Include common submodule
  include openconfig-ospf-common;

  // meta
  organization "OpenConfig working group";

  contact
    "OpenConfig working group
    www.openconfig.net";

  description
    "This submodule provides common OSPF configuration and operational
    state parameters that are global to a particular OSPF instance";

  oc-ext:openconfig-version "0.7.0";

  revision "2026-09-11" {
    description
      "Add minimum-hold leaf to OSPF global timers, equivalent to
      spf-second-interval and lsp-second-wait-interval of IS-IS
      global timers.";
    reference "0.7.0";
  }
  revision "2026-09-10" {
    description
      "Add send-default-route container to the OSPF global
      structure, allowing origination of a default external route,
      equivalent to send-default-route of BGP global and neighbors
      config.";
    reference "0.6.0";
  }
  revision "2026-09-09" {
    description
      "Add nsr container to OSPF global structure, equivalent to
      that of ISIS global config.";
    reference "0.5.0";
  }
  revision "2026-09-08" {
    description
      "Add max-ecmp-paths leaf to OSPF global config, equivalent to
      that of ISIS global config.";
    reference "0.4.0";
  }
  revision "2026-09-07" {
    description
      "Add reference-bandwidth container to OSPF global structure,
      equivalent to that of ISIS global config.";
    reference "0.3.0";
  }
  revision "2026-09-06" {
    description
      "Add route-preference container to OSPF global structure,
      providing administrative distance (preference) leafs for
      intra-area, inter-area and external OSPF routes, equivalent to
      those of ISIS global config.";
    reference "0.2.0";
  }
  revision "2025-08-10" {
    description
      "Removed duplicate import and updated prefixes in openconfig-ospf-area";
    reference "0.1.1";
  }
  revision "2025-02-13" {
    description
      "Initial revision";
    reference "0.0.1";
  }

  grouping ospf-global-config {
    description
      "Global configuration for OSPF";

    leaf router-id {
      type yang:dotted-quad;
      description
        "A 32-bit number represented as a dotted quad assigned to
        each router running the OSPF protocol. This number should
        be unique within the autonomous system";
      reference "rfc2828";
    }

    leaf log-adjacency-changes {
      type boolean;
      description
        "When this leaf is set to true, a log message will be
        generated when the state of an OSPF neighbour changes.";
    }

    leaf hide-transit-only-networks {
      type boolean;
      description
        "When this leaf is set to true, do not advertise prefixes
        into OSPF that correspond to transit interfaces, as per
        the behaviour discussed in RFC6860.";
      reference
        "RFC6860 - Hiding Transit-Only Networks in OSPF";
    }

    leaf abr-capability {
      type identityref {
        base "oc-ospft:OSPF_ABR_TYPE";
      }
      description
        "When the leaf is set to RFC2328_ABR, the router
         acts as an ABR when it participates in multiple OSPF
         areas. It does not matter whether the backbone area
         exists or not. When the leaf is set to RFC3509_ABR,
         the router acts as an ABR when the router participates
         in multiple OSPF areas, one of which must be backbone.";
    }

    leaf max-ecmp-paths {
      type uint8;
      description
        "The maximum number of equal-cost paths that OSPF can
        install for a single destination. Equivalent to the
        max-ecmp-paths of ISIS global config.";
    }
  }

  grouping ospf-global-spf-timers-config {
    description
      "Configuration parameters relating to global SPF timer
      parameters for OSPF";

    leaf initial-delay {
      // rjs TODO: IS-IS model has this as decimal64 - should it be
      // that or uint32 msec?
      type uint32;
      units msec;
      description
        "The value of this leaf specifies the time between a change
        in topology being detected and the first run of the SPF
        algorithm.";
    }

    leaf minimum-hold {
      type uint32;
      units msec;
      description
        "The value of this leaf specifies the minimum hold time
        between consecutive SPF runs. Equivalent to
        spf-second-interval of IS-IS SPF timer.";
    }

    leaf maximum-delay {
      // rjs TODO: same question as above
      type uint32;
      units msec;
      description
        "The value of this leaf specifies the maximum delay between
        a topology change being detected and the SPF algorithm
        running. This value is used for implementations that support
        increasing the wait time between SPF runs.";
    }
  }

  grouping ospf-global-lsa-generation-timers-config {
    description
      "Configuration parameters relating to global LSA generation
      parameters for OSPF";

    leaf initial-delay {
      type uint32;
      units msec;
      description
        "The value of this leaf specifies the time between the first
        time an LSA is generated and advertised and the subsequent
        generation of that LSA.";
    }

    leaf minimum-hold {
      type uint32;
      units msec;
      description
        "The value of this leaf specifies the minimum hold time
        between consecutive generations of an LSA. Equivalent to
        lsp-second-wait-interval of IS-IS LSP generation timer.";
    }

    leaf maximum-delay {
      type uint32;
      units msec;
      description
        "The value of this leaf specifies the maximum time between the
        generation of an LSA and the subsequent re-generation of that
        LSA. This value is used in implementations that support
        increasing delay between generation of an LSA";
    }
  }

  grouping ospf-global-spf-timers-state {
    description
      "Operational state parameters relating to OSPF global
      timers";

    uses ospf-common-timers;
  }

  grouping ospf-global-lsa-generation-timers-state {
    description
      "Operational state parameters relating to OSPF global
      timers";

    uses ospf-common-timers;
  }

  grouping ospf-global-graceful-restart-config {
    description
      "Configuration parameters relating to graceful restart for
      OSPF";

    leaf enabled {
      type boolean;
      description
        "When the value of this leaf is set to true, graceful restart
        is enabled on the local system. In this case, the system will
        use Grace-LSAs to signal that it is restarting to its
        neighbors.";
    }

    leaf helper-only {
      type boolean;
      description
        "Operate graceful-restart only in helper mode. When this leaf
        is set to true, the local system does not use Grace-LSAs to
        indicate that it is restarting, but will accept Grace-LSAs
        from remote systems, and suppress withdrawl of adjacencies
        of the system for the grace period specified";
    }
  }

  grouping ospf-global-inter-areapp-config {
    description
      "Configuration parameters for OSPF policies which propagate
      prefixes between areas";

    leaf src-area {
      type leafref {
        // we are at ospf/global/inter-area-propagation-policies/...
        // inter-area-propagation-policy/config/src-area
        path "../../../../../areas/area/identifier";
      }
      description
        "The area from which prefixes are to be exported.";
    }

    leaf dst-area {
      type leafref {
        // we are at ospf/global/inter-area-propagation-policies/...
        // inter-area-propagation-policy/config/src-area
        path "../../../../../areas/area/identifier";
      }
      description
        "The destination area to which prefixes are to be imported";
    }

    uses oc-rpol:apply-policy-import-config;
    uses oc-rpol:default-policy-import-config;
  }

  grouping ospf-global-route-preference-config {
    description
      "Configuration options relating to the administrative distance
      (preference) assigned to routes per different OSPF route type,
      intra-area, inter-area and external routes. Equivalent to
      external-route-preference and internal-route-preference of
      ISIS route-preference grouping.";

    leaf intra-area-route-preference {
      type uint8 {
        range "1..255";
      }
      description
        "Administrative distance (preference) for intra-area OSPF
        routes.";
    }

    leaf inter-area-route-preference {
      type uint8 {
        range "1..255";
      }
      description
        "Administrative distance (preference) for inter-area OSPF
        routes.";
    }

    leaf external-route-preference {
      type uint8 {
        range "1..255";
      }
      description
        "Administrative distance (preference) for external OSPF
        routes.";
    }
  }

  grouping ospf-global-reference-bandwidth-config {
    description
      "Configuration parameters relating to the OSPF auto-cost
      reference bandwidth.";

    leaf reference-bandwidth {
      type uint32;
      units Mbps;
      description
        "The reference bandwidth, in Mbps, used by the local
        system to calculate the default metric for an interface
        based on its bandwidth. Equivalent to the
        reference-bandwidth leaf on the ISIS global config.";
    }
  }

  grouping ospf-global-admin-config {
    description
      "Re-usable grouping to enable or disable a particular OSPF
      feature.";

    leaf enabled {
      type boolean;
      description
        "When set to true, the functionality within which this leaf
        is defined is enabled; when set to false it is explicitly
        disabled.";
    }
  }

  grouping ospf-global-send-default-route-config {
    description
      "Configuration parameters relating to origination of a default
      external route into the local OSPF instance.";

    leaf enabled {
      type boolean;
      default false;
      description
        "When set to true, originate a default external route,
        subject to the values of the always, metric, and
        metric-type leafs.";
    }

    leaf always {
      type boolean;
      default false;
      description
        "When set to true, originate a default external route even
        when no default route exists in the local system's routing
        information base. When set to false (default), the default
        external route is only originated when a default route is
        already present locally.";
    }

    leaf metric {
      type uint32 {
        range "0..16777214";
      }
      description
        "The metric to advertise for the originated default
        external route.";
    }

    leaf metric-type {
      type enumeration {
        enum EXTERNAL_TYPE_1 {
          description
            "Advertise the default external route with an OSPF
            external route type 1.";
        }
        enum EXTERNAL_TYPE_2 {
          description
            "Advertise the default external route with an OSPF
            external route type 2.";
        }
      }
      default "EXTERNAL_TYPE_2";
      description
        "Specify the external route type with which the default
        external route is advertised.";
    }
  }

  grouping ospf-global-max-metric-config {
    description
      "Configuration paramters relating to setting the OSPF
      maximum metric.";

    leaf set {
      type boolean;
      description
        "When this leaf is set to true, all non-stub interfaces of
        the local system are advertised with the maximum metric,
        such that the router does not act as a transit system,
        (similarly to the IS-IS overload functionality).";
      reference
        "RFC3137 - OSPF Stub Router Advertisement";
    }

    leaf timeout {
      type uint64;
      units "seconds";
      description
        "The delay, in seconds, after which the advertisement of
        entities with the maximum metric should be cleared, and
        the system reverts to the default, or configured, metrics.";
    }

    leaf-list include {
      type identityref {
        base "oc-ospft:MAX_METRIC_INCLUDE";
      }
      description
        "By default, the maximum metric is advertised for all
        non-stub interfaces of a device. When identities are
        specified within this leaf-list, additional entities
        are also advertised with the maximum metric according
        to the values within the list.";
    }

    leaf-list trigger {
      type identityref {
        base "oc-ospft:MAX_METRIC_TRIGGER";
      }
      description
        "By default, the maximum metric is only advertised
        when the max-metric/set leaf is specified as true.
        In the case that identities are specified within this
        list, they provide additional triggers (e.g., system
        boot) that may cause the max-metric to be set. In this
        case, the system should still honour the timeout specified
        by the max-metric/timeout leaf, and clear the max-metric
        advertisements after the expiration of this timer.";
    }
  }

  grouping ospf-global-structural {
    description
      "Top level structural grouping for OSPF global parameters";

    container global {
      description
        "Configuration and operational state parameters for settings
        that are global to the OSPF instance";

      container config {
        description
          "Global configuration parameters for OSPF";
        uses ospf-global-config;
      }

      container state {
        config false;
        description
          "Operational state parameters for OSPF";
        uses ospf-global-config;
      }

      container timers {
        description
          "Configuration and operational state parameters for OSPF
          timers";

        container spf {
          description
            "Configuration and operational state parameters relating
            to timers governing the operation of SPF runs";

          container config {
            description
              "Configuration parameters relating to global OSPF
              SPF timers";
            uses ospf-global-spf-timers-config;
          }

          container state {
            config false;
            description
              "Operational state parameters relating to the global
              OSPF SPF timers";
            uses ospf-global-spf-timers-config;
            uses ospf-global-spf-timers-state;
          }
        }

        container max-metric {
          description
            "Configuration and operational state parameters relating
            to setting the OSPF maximum metric.";

          container config {
            description
              "Configuration parameters relating to setting the OSPF
              maximum metric for a set of advertised entities.";
            uses ospf-global-max-metric-config;
          }

          container state {
            config false;
            description
              "Operational state parameters relating to setting the
              OSPF maximum metric for a set of advertised entities.";
            uses ospf-global-max-metric-config;
          }
        }

        container lsa-generation {
          description
            "Configuration and operational state parameters relating
            to timers governing the generation of LSAs by the local
            system";

          container config {
            description
              "Configuration parameters relating to the generation of
              LSAs by the local system";
            uses ospf-global-lsa-generation-timers-config;
          }

          container state {
            config false;
            description
              "Operational state parameters relating to the generation
              of LSAs by the local system";
            uses ospf-global-lsa-generation-timers-config;
            uses ospf-global-lsa-generation-timers-state;
          }
        }
      }

      container graceful-restart {
        description
          "Configuration and operational state parameters for OSPF
          graceful restart";

        container config {
          description
            "Configuration parameters relating to OSPF graceful
            restart";
          uses ospf-global-graceful-restart-config;
        }

        container state {
          config false;
          description
            "Operational state parameters relating to OSPF graceful
            restart";
          uses ospf-global-graceful-restart-config;
        }
      }

      container inter-area-propagation-policies {
        description
          "Policies defining how inter-area propagation should be performed
          by the OSPF instance";

        list inter-area-propagation-policy {
          key "src-area dst-area";
          description
            "A list of connections between pairs of areas - routes are
            propagated from the source (src) area to the destination (dst)
            area according to the policy specified";

          leaf src-area {
            type leafref {
              path "../config/src-area";
            }
            description
              "Reference to the source area";
          }

          leaf dst-area {
            type leafref {
              path "../config/dst-area";
            }
            description
              "Reference to the destination area";
          }

          container config {
            description
              "Configuration parameters relating to the inter-area
              propagation policy";
            uses ospf-global-inter-areapp-config;
          }

          container state {
            config false;
            description
              "Operational state parameters relating to the inter-area
              propagation policy";
            uses ospf-global-inter-areapp-config;
          }
        }
      }

      container route-preference {
        description
          "Administrative distance (preference) assigned to routes
          per different OSPF route type, intra-area, inter-area,
          external routes.";

        container config {
          description
            "Configuration parameters relating to the OSPF route
            preference";
          uses ospf-global-route-preference-config;
        }

        container state {
          config false;
          description
            "State information relating to the OSPF route
            preference";
          uses ospf-global-route-preference-config;
        }
      }

      container reference-bandwidth {
        description
          "Configuration and operational state parameters relating
          to the OSPF auto-cost reference bandwidth.";

        container config {
          description
            "Configuration parameters relating to the OSPF auto-cost
            reference bandwidth.";
          uses ospf-global-reference-bandwidth-config;
        }

        container state {
          config false;
          description
            "Operational state parameters relating to the OSPF
            auto-cost reference bandwidth.";
          uses ospf-global-reference-bandwidth-config;
        }
      }

      container nsr {
        description
          "Configuration and operational state parameters for OSPF
          Non-Stop Routing (NSR)";

        container config {
          description
            "Configuration parameters relating to OSPF Non-Stop
            Routing (NSR)";
          uses ospf-global-admin-config;
        }

        container state {
          config false;
          description
            "Operational state parameters relating to OSPF Non-Stop
            Routing (NSR)";
          uses ospf-global-admin-config;
        }
      }

      container send-default-route {
        description
          "Configuration and operational state parameters relating
          to origination of a default external route into the local
          OSPF instance.";

        container config {
          description
            "Configuration parameters relating to origination of a
            default external route.";
          uses ospf-global-send-default-route-config;
        }

        container state {
          config false;
          description
            "Operational state parameters relating to origination
            of a default external route.";
          uses ospf-global-send-default-route-config;
        }
      }
    }
  }
}
