module openconfig-icmpv4-types {

  yang-version "1";
  namespace "http://openconfig.net/yang/openconfig-icmpv4-types";

  prefix "oc-icmpv4-types";

  import openconfig-extensions { prefix oc-ext; }

  organization "OpenConfig working group";

  contact
    "OpenConfig working group
    www.openconfig.net";

  description
    "OpenConfig module defining the types and coresponding codes for
    ICMPv4.";

  oc-ext:openconfig-version "0.1.0";

  revision "2023-01-26" {
    description
      "Initial revision of ICMPv4 types module.";
    reference "0.1.0";
  }

  identity TYPE {
    description
      "Base identity for ICMPv4 codes";
  }

  identity CODE {
    description
      "Base identity for ICMPv4 codes.";
  }

  identity ECHO_REPLY {
    description
      "ICMP echo reply, value 0.";
    base TYPE;
    reference "RFC792: INTERNET CONTROL MESSAGE PROTOCOL";
  }

  identity DST_UNREACHABLE {
    description
      "ICMP destination unreachable, value 3.";
    base TYPE;
    reference "RFC792: INTERNET CONTROL MESSAGE PROTOCOL";
  }

  identity REDIRECT {
    description
      "ICMP redirect, value 5.";
    base TYPE;
    reference "RFC792: INTERNET CONTROL MESSAGE PROTOCOL";
  }

  identity ECHO {
    description
      "ICMP echo, value 8.";
    base TYPE;
    reference "RFC792: INTERNET CONTROL MESSAGE PROTOCOL";
  }

  identity ROUTER_ADVERTISEMENT {
    description
      "ICMP router advertisement, value 9.";
    base TYPE;
    reference "RFC1256: ICMP Router Discovery Messages";
  }

  identity ROUTER_SOLICITATION {
    description
      "ICMP Router Solicitation, value 10.";
    base TYPE;
    reference "RFC1256: ICMP Router Discovery Messages";
  }

  identity TIME_EXCEEDED {
    description
      "ICMP TTL exceede, value 11.";
    base TYPE;
    reference "RFC792: INTERNET CONTROL MESSAGE PROTOCOL";
  }

  identity PARAM_PROBLEM {
    description
      "ICMP parameter problem, value 12.";
    base TYPE;
    reference "RFC792: INTERNET CONTROL MESSAGE PROTOCOL";
  }

  identity TIMESTAMP {
    description
      "ICMP timestamp, value 13.";
    base TYPE;
    reference "RFC792: INTERNET CONTROL MESSAGE PROTOCOL";
  }

  identity TIMESTAMP_REPLY {
    description
      "ICMP timestamp reply, value 14.";
    base TYPE;
    reference "RFC792: INTERNET CONTROL MESSAGE PROTOCOL";
  }
  identity TRACEROUTE{
    description
      "Traceroute (deprecated), value 30.";
    base TYPE;
    reference "RFC1393: Traceroute Using an IP Option";
  }
  identity PHOTURIS {
    description
      "ICMP Photuris, value 40.";
    base TYPE;
    reference "RFC2521: CMP Security Failures Messages";
  }

  identity EXT_ECHO_REQUEST {
    description
      "ICMP extended echo request, value 42.";
    base TYPE;
    reference "RFC8335: PROBE: A Utility for Probing Interfaces";
  }

  identity EXT_ECHO_REPLY {
    description
      "ICMP extended echo reply, value 43.";
    base TYPE;
    reference "RFC8335: PROBE: A Utility for Probing Interfaces";
  }

  identity ECHO_REPLY_CODE {
    description
      "CODE for ICMPv4 Echo Reply.";
    base CODE;
  }

  identity ECHO_REPLY_NONE {
    description
      "No code, type 0 for Echo Reply.";
    base ECHO_REPLY_CODE;
    reference "RFC792: INTERNET CONTROL MESSAGE PROTOCOL";
  }

  identity DST_UNREACHABLE_CODE {
    description
      "Codes for ICMPv4 Destination Unreachable.";
    base CODE;
  }

  identity DST_UNREACHABLE_NET {
    description
      "ICMPv4 destination network unreachable, code 0.";
    base DST_UNREACHABLE_CODE;
    reference "RFC792: INTERNET CONTROL MESSAGE PROTOCOL";
  }

  identity DST_UNREACHABLE_HOST {
    description
      "ICMPv4 destination host unreachable, code 1";
    base DST_UNREACHABLE_CODE;
    reference "RFC792: INTERNET CONTROL MESSAGE PROTOCOL";
  }

  identity DST_UNREACHABLE_PROTOCOL {
    description
      "ICMPv4 destination protocol unreachable, code 2.";
    base DST_UNREACHABLE_CODE;
    reference "RFC792: INTERNET CONTROL MESSAGE PROTOCOL";
  }

  identity DST_UNREACHABLE_PORT {
    description
      "ICMPv4 Port unreachable, code 3.";
    base DST_UNREACHABLE_CODE;
    reference "RFC792: INTERNET CONTROL MESSAGE PROTOCOL";
  }

  identity DST_UNREACHABLE_CANNOT_FRAGMENT {
    description
      "ICMPv4 destination unreachable due to inability to fragment. The df-bit
      is set but the packet requires fragmentation, code 4.";
    base DST_UNREACHABLE_CODE;
    reference "RFC792: INTERNET CONTROL MESSAGE PROTOCOL";
  }

  identity DST_UNREACHABLE_SRC_ROUTE_FAILED {
    description
      "ICMPv4 destination is unreachable as source routing failed, code 5.";
    base DST_UNREACHABLE_CODE;
    reference "RFC792: INTERNET CONTROL MESSAGE PROTOCOL";
  }

  identity DST_UNREACHABLE_DST_NET_UNKNOWN {
    description
      "ICMPv4 destination is unreachable as the destination network is
      unknown, code 6.";
    base DST_UNREACHABLE_CODE;
    reference "RFC1122: Requirements for Internet Hosts --
              Communication Layers";
  }

  identity DST_UNREACHABLE_DST_HOST_UNKNOWN {
    description
      "ICMPv4 destination is unreachable as the destination host is unknown, code 7.";
    base DST_UNREACHABLE_CODE;
    reference "RFC1122: Requirements for Internet Hosts --
          Communication Layers";
  }

  identity DST_UNREACHABLE_SRC_HOST_ISOLATED {
    description
      "ICMPv4 destination unreachable as the source host is isolated, code 8.";
    base DST_UNREACHABLE_CODE;
    reference "RFC1122: Requirements for Internet Hosts --
              Communication Layers";
  }

  identity DST_UNREACHABLE_DST_NET_ADMIN_PROHIBITED {
    description
      "ICMPv4 destination is unreachable as communication with the destination
      network is administratively prohibited, code 9.";
    base DST_UNREACHABLE_CODE;
    reference "RFC1122: Requirements for Internet Hosts --
              Communication Layers";
  }

  identity DST_UNREACHABLE_DST_HOST_ADMIN_PROHIBITED {
    description
      "ICMPv4 destination is unreachable as communication with the destination
      host is adminstratively prohibited, code 10.";
    base DST_UNREACHABLE_CODE;
    reference "RFC1122: Requirements for Internet Hosts --
              Communication Layers";
  }

  identity DST_UNREACHABLE_NET_UNREACHABLE_FOR_TOS {
    description
      "ICMPv4 destination network is unreachable for the specified type of
      service, code 11.";
    base DST_UNREACHABLE_CODE;
    reference "RFC1122: Requirements for Internet Hosts --
              Communication Layers";
  }

  identity DST_UNREACHABLE_HOST_UNREACHABLE_FOR_TOS {
    description
      "ICMPv4 destination host is unreachable for the specified type of
      service, code 12.";
    base DST_UNREACHABLE_CODE;
    reference "RFC1122: Requirements for Internet Hosts --
              Communication Layers";
  }

  identity DST_UNREACHABLE_ADMIN_PROHIBITED {
    description
      "ICMPv4 destination is unreacable as packets were adminstratively
      filtered.";
    base DST_UNREACHABLE_CODE;
    reference "RFC1812: Requirements for IP Version 4 Routers";
  }

  identity DST_UNREACHABLE_HOST_PRECEDENCE_VIOLATION {
    description
      "ICMPv4 destination is unreachable as the first-hop router has determined
      that the destination cannot be reached for the specified source/
      destination host, network, upper-layer protocol and source/destination
      port. Code 14";
    base DST_UNREACHABLE_CODE;
  }

  identity DST_UNREACHABLE_PRECEDENCE_CUTOFF {
    description
      "ICMPv4 Precedence cutoff in effect.  The network operators have imposed
        a minimum level of precedence required for operation, the
        datagram was sent with a precedence below this level.
        Code 15.
      that the destination cannot be reached for the specified source/
    base DST_UNREACHABLE_CODE;
    reference "RFC1812: Requirements for IP Version 4 Routers";
  }

  identity REDIRECT_CODE {
    base CODE;
    description
      "Codes for the ICMPv4 Redirect type.";
  }

  identity REDIRECT_NETWORK {
    base REDIRECT_CODE;
    description
      "ICMP redirect is being issued for the network or subnet,
       code 0";
    reference "RFC792: INTERNET CONTROL MESSAGE PROTOCOL";
  }

  identity REDIRECT_HOST {
    base REDIRECT_CODE;
    description
      "ICMP redirect is being issued for the host, code 1.";
    reference "RFC792: INTERNET CONTROL MESSAGE PROTOCOL";
  }

  identity REDIRECT_TOS_NETWORK {
    base REDIRECT_CODE;
    description
      "ICMP redirect is being issued for the network and type of service. code 2.";
    reference "RFC792: INTERNET CONTROL MESSAGE PROTOCOL";
  }

  identity REDIRECT_TOS_HOST {
    base REDIRECT_CODE;
    description
      "ICMP redirect is being issued for the host and type of service,
      code 3";
    reference "RFC792: INTERNET CONTROL MESSAGE PROTOCOL";
  }

  identity ECHO_CODE {
    base CODE;
    description
      "Codes for ICMPv4 echo messages.";
    reference "RFC792: INTERNET CONTROL MESSAGE PROTOCOL";
  }

  identity ECHO_NO_CODE {
    base ECHO_CODE;
    description
      "No code.";
    reference "RFC792: INTERNET CONTROL MESSAGE PROTOCOL";
  }

  identity ROUTER_ADVERTISEMENT_CODE {
    base CODE;
    description
      "Code for the ICMPv4 router advertisement message.";
  }
  identity ROUTER_ADVERTISEMENT_NORMAL {
    base ROUTER_ADVERTISEMENT_CODE;
    description
      "Code 0: Normal router advertisement.";
    reference "RFC3344: IP Mobility Support for IPv4";
  }

  identity ROUTER_ADVERTISEMENT_DOES_NOT_ROUTE_COMMON {
    base ROUTER_ADVERTISEMENT_CODE;
    description
      "Code 16: Does not route common traffic.";
    reference "RFC3344: IP Mobility Support for IPv4";
  }

  identity ROUTER_SELECTION_CODE {
    base CODE;
    description
      "Codes for the ICMPv4 router selection message.";
  }

  identity ROUTER_SELECTION_NO_CODE {
    base ROUTER_SELECTION_CODE;
    description
      "No code.";
    reference "RFC1256: ICMP Router Discovery Messages";
  }

  identity TIME_EXCEEDED_CODE {
    base CODE;
    description
      "Codes for the ICMPv4 time exceeded code.";
  }

  identity TIME_EXCEEDED_IN_TRANSIT {
    base TIME_EXCEEDED_CODE;
    description
      "Code 0: Time to Live exceeded in Transit.";
    reference "RFC792: INTERNET CONTROL MESSAGE PROTOCOL";
  }

  identity TIME_EXCEEDED_FRAGMENT_REASSEMBLY_IN_TRANSIT {
    base TIME_EXCEEDED_CODE;
    description
      "Code 1: Fragment reassembly time exceeded.";
    reference "RFC792: INTERNET CONTROL MESSAGE PROTOCOL";
  }

  identity PARAM_PROBLEM_CODE {
    base CODE;
    description
      "Codes for the ICMPv4 parameter problem message (Type 12).";
  }

  identity PARAM_PROBLEM_POINTER_INDICATES_ERR {
    base PARAM_PROBLEM_CODE;
    description
      "Code 0: Pointer indicates the error.";
    reference "RFC792: INTERNET CONTROL MESSAGE PROTOCOL";
  }

  identity PARAM_PROBLEM_MISSING_REQ_OPTION {
    base PARAM_PROBLEM_CODE;
    description
      "Code 1: Missing a required option.";
    reference "RFC1108: U.S. Department of Defense
               Security Options for the Internet Protocol";
  }

  identity PARAM_PROBLEM_BAD_LENGTH {
    base PARAM_PROBLEM_CODE;
    description
      "Code 2: Bad Length.";
    reference "RFC792: INTERNET CONTROL MESSAGE PROTOCOL";
  }

  identity TIMESTAMP_CODE {
    base CODE;
    description
      "Codes of the ICMPv4 timestamp message (Type 13).";
  }
  identity TIMESTAMP_NO_CODE {
    base TIMESTAMP_CODE;
    description
      "No code.";
    reference "RFC792: INTERNET CONTROL MESSAGE PROTOCOL";
  }

  identity TIMESTAMP_REPLY_CODE {
    base CODE;
    description
      "Codes of the ICMPv4 timestamp reply message (Type 14).";
  }

  identity TIMESTAMP_REPLY_NO_CODE {
    base TIMESTAMP_REPLY_CODE;
    description
      "No code.";
    reference "RFC792: INTERNET CONTROL MESSAGE PROTOCOL";
  }

  identity PHOTURIS_CODE {
    base CODE;
    description
      "Codes of the ICMPv4 Photuris message (type 40).";
  }

  identity PHOTURIS_BAD_SPI {
    base PHOTURIS_CODE;
    description
      "Code 0: Bad SPI.";
    reference "RFC2521: ICMP Security Failures Messages";
  }

  identity PHOTURIS_AUTH_FAILED {
    base PHOTURIS_CODE;
    description
      "Code 1: Authentication failed.";
    reference "RFC2521: ICMP Security Failures Messages";
  }

  identity PHOTURIS_DECOMPRESS_FAILED {
    base PHOTURIS_CODE;
    description
      "Code 2: Decompression failed.";
    reference "RFC2521: ICMP Security Failures Messages";
  }

  identity PHOTURIS_DECRYPTION_FAILED {
    base PHOTURIS_CODE;
    description
      "Code 3: Decryption failed.";
    reference "RFC2521: ICMP Security Failures Messages";
  }

  identity PHOTURIS_NEED_AUTHENTICATION {
    base PHOTURIS_CODE;
    description
      "Code 4: Need authentication.";
    reference "RFC2521: ICMP Security Failures Messages";
  }

  identity PHOTURIS_NEED_AUTHORIZATION {
    base PHOTURIS_CODE;
    description
      "Code 5: Need authorization.";
    reference "RFC2521: ICMP Security Failures Messages";
  }

  identity EXT_ECHO_REQUEST_CODE {
    description
      "Codes of the extended echo request ICMP message.";
    base CODE;
  }

  identity EXT_ECHO_REQUEST_NO_ERROR {
    base EXT_ECHO_REQUEST_CODE;
    description
      "Code 0: No error.";
    reference "RFC8335: PROBE: A Utility for Probing Interfaces";
  }

  identity EXT_ECHO_REPLY_CODE {
    description
      "Codes of the extended echo reply ICMP message (Type 43).";
    base CODE;
  }

  identity EXT_ECHO_REPLY_NO_ERROR {
    base EXT_ECHO_REPLY_CODE;
    description
      "Code 0: No error.";
    reference "RFC8335: PROBE: A Utility for Probing Interfaces";
  }

  identity EXT_ECHO_REPLY_MALFORMED_QUERY {
    base EXT_ECHO_REPLY_CODE;
    description
      "Code 1: Malformed query.";
    reference "RFC8335: PROBE: A Utility for Probing Interfaces";
  }

  identity EXT_ECHO_REPLY_NO_SUCH_INTF {
    base EXT_ECHO_REPLY_CODE;
    description
      "Code 2: No such interface.";
    reference "RFC8335: PROBE: A Utility for Probing Interfaces";
  }

  identity EXT_ECHO_REPLY_NO_SUB_TABLE_ENTRY {
    base EXT_ECHO_REPLY_CODE;
    description
      "Code 3: No such table entry.";
    reference "RFC8335: PROBE: A Utility for Probing Interfaces";
  }

  identity EXT_ECHO_REPLY_MULTIPLE_INTF_SATISFY_QUERY {
    base EXT_ECHO_REPLY_CODE;
    description
      "Code 4: Multiple interfaces satisfy query.";
    reference "RFC8335: PROBE: A Utility for Probing Interfaces";
  }
}
