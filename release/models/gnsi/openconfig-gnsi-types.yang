module openconfig-gnsi-types {
  yang-version "1";
  namespace "http://openconfig.net/yang/gnsi/types";
  prefix "oc-gnsit";

  import openconfig-extensions {
    prefix oc-ext;
  }

  import openconfig-grpc-types {
    prefix oc-grpct;
  }

  organization
    "OpenConfig Working Group";

  contact
    "OpenConfig working group
    netopenconfig@googlegroups.com";

  description
    "This module defines a set of extensions that provide gNSI (the gRPC
    Network Security Interface) specific extensions to the OpenConfig data models.
    Specifically, the parameters for the configuration of the service, and
    configuration and state are added.

    The gNSI protobufs and documentation are published at
    https://github.com/openconfig/gnsi.";

  oc-ext:openconfig-version "0.2.0";

  revision 2024-04-23 {
    description
      "Initial revision.";
    reference "0.1.0";
  }

  identity GNSI {
    base "oc-grpct:GRPC_SERVICE";
    description
      "gNSI: gRPC Network Security Interface";
  }
}
