module openconfig-sampling-gnpsi {
  yang-version "1";

  // namespace
  namespace "http://openconfig.net/yang/sampling/gnpsi";

  prefix "oc-gnpsi";

  // import some basic types
  import openconfig-extensions { prefix oc-ext; }
  import openconfig-inet-types { prefix oc-inet; }
  import openconfig-yang-types { prefix oc-yang; }
  import openconfig-system { prefix oc-sys; }
  import openconfig-system-grpc { prefix oc-sys-grpc; }

  // meta
  organization "OpenConfig working group";

  contact
    "OpenConfig working group
    www.openconfig.net";

  description
    "This module defines configuration and operational state data
    related to gRPC Network Packet Sampling Interface.";

  revision "2024-04-01" {
    description
      "Initial revision";
    reference "0.1.0";
  }

  oc-ext:openconfig-version "1.0.0";


  grouping gnpsi-collectors-state {
    description
      "Operational data for gNPSI collectors.";

    leaf address {
      type oc-inet:ip-address;
      description
        "IPv4/IPv6 address of the gNPSI collector.";
    }

    leaf port {
      type oc-inet:port-number;
      default 6343;
      description
        "UDP port number for the gNPSI collector.";
    }

    leaf bytes-sent {
      type oc-yang:counter64;
      description
        "The total number of bytes sampled and sent to the
        collector.";
    }

    leaf packets-sent {
      type oc-yang:counter64;
      description
        "The total number of packets sampled and sent to the
        collector.";
    }

    leaf packets-error {
      type oc-yang:counter64;
      description
        "The total number of error packets failed to be sampled
        and sent to the collector.";
    }
  }

  grouping gnpsi-collectors-top {
    description
      "Top-level grouping for data related to gNPSI collectors.";

    container collectors {
      config false;
      description
        "Enclosing container for list of gNPSI collectors.";

      list collector {
        key "address port";
        description
          "List of gNPSI collectors to send sampling data.  Packet
          samples are sent to all collectors specified.";

        leaf address {
          type leafref {
            path "../state/address";
          }
          description
            "Reference to address list key.";
        }

        leaf port {
          type leafref {
            path "../state/port";
          }
          description
            "Reference to port list key.";
        }

        container state {
          config false;
          description
            "Operational state data for gNPSI collectors.";

          uses gnpsi-collectors-state;
        }
      }
    }
  }

  augment "/oc-sys:system/oc-sys-grpc:grpc-servers/oc-sys-grpc:grpc-server" {
    description
      "Add gNPSI configuration/state to the openconfig-sampling model.";

    uses gnpsi-collectors-top;
  }
}
