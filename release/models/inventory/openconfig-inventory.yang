module openconfig-inventory {

  yang-version "1";

  // namespace
  namespace "http://openconfig.net/yang/inventory";

  prefix "oc-inv";

  import openconfig-inventory-types { prefix oc-inv-types; }
  import openconfig-interfaces { prefix ocif; }
  import openconfig-extensions { prefix oc-ext; }


  // meta
  organization "OpenConfig working group";

  contact
    "OpenConfig working group
    www.openconfig.net";

  description
    "This module defines a data model for representing a system
    component inventory, which can include hardware or software
    elements arranged in an arbitrary structure. The primary
    relationship supported by the model is containment, e.g.,
    components containing subcomponents.

    It is expected that this model reflects every field replacable
    unit on the device at a minimum (i.e., additional information
    may be supplied about non-replacable components).

    Every element in the inventory is termed a 'component' with each
    component expected to have a unique name and type, and optionally
    a unique system-assigned identifier and FRU number.  The
    uniqueness is guaranteed by the system within the device.

    Components may have properties defined by the system that are
    modeled as a list of key-value pairs. These may or may not be
    user-configurable.  The model provides a flag for the system
    to optionally indicate which properties are user configurable.

    Each component also has a list of 'subcomponents' which are
    references to other components. Appearance in a list of
    subcomponents indicates a containment relationship as described
    above.  For example, a linecard component may have a list of
    references to port components that reside on the linecard.

    This schema is generic to allow devices to express their own
    platform-specific structure.  It may be augmented by additional
    component type-specific schemas that provide a common structure
    for well-known component types.  In these cases, the system is
    expected to populate the common component schema, and may
    optionally also represent the component and its properties in the
    generic structure.

    The properties for each component may include dynamic values,
    e.g., in the 'state' part of the schema.  For example, a CPU
    component may report its utilization, temperature, or other
    physical properties.  The intent is to capture all platform-
    specific physical data in one location, including inventory
    (presence or absence of a component) and state (physical
    attributes or status).";

  oc-ext:openconfig-version "0.1.0";

  revision "2015-12-18" {
    description
      "Initial public release";
    reference "0.1.0";
  }

  revision "2015-09-08" {
    description
      "Initial revision";
    reference "Pre-release";
  }

  // grouping statements


  grouping inventory-component-properties-config {
    description
      "System-defined configuration data for component properties";

    leaf name {
      type string;
      description
        "System-supplied name of the property -- this is typically
        non-configurable";
    }

    leaf value {
      type union {
        type string;
        type boolean;
        type int64;
        type uint64;
        type decimal64 {
          fraction-digits 2;
        }
      }
      description
        "Property values can take on a variety of types.  Signed and
        unsigned integer types may be provided in smaller sizes,
        e.g., int8, uint16, etc.";
    }
  }

  grouping inventory-component-properties-state {
    description
      "Operational state data for component properties";

    leaf configurable {
      type boolean;
      description
        "Indication whether the property is user-configurable";
    }
  }

  grouping inventory-component-properties-top {
    description
      "Top-level grouping ";

    container properties {
      description
        "Enclosing container ";

      list property {
        key name;
        description
          "List of system properties for the component";

        leaf name {
          type leafref {
            path "../config/name";
          }
          description
            "Reference to the property name.";
        }

        container config {
          description
            "Configuration data for each property";

          uses inventory-component-properties-config;
        }

        container state {

          config false;

          description
            "Operational state data for each property";

          uses inventory-component-properties-config;
          uses inventory-component-properties-state;
        }
      }
    }
  }

  grouping inventory-subcomponent-ref-config {
    description
      "Configuration data for subcomponent references";

    leaf name {
      type string;
      description
        "Name of the subcomponent -- should reflect the name of
        the referenced component";
    }
  }

  grouping inventory-subcomponent-ref-state {
    description
      "Operational state data for subcomponent references";

    //TODO: the name itself could perhaps be the reference to the
    //component
    leaf reference {
      type leafref {
        path "../../../../../component/name";
      }
      description
        "References the corresponding component in the overall
        list of inventory components";
    }
  }

  grouping inventory-subcomponent-ref-top {
    description
      "Top-level grouping for list of subcomponent references";

    container subcomponents {
      description
        "Enclosing container for subcomponent references";

      list subcomponent {
        key name;
        description
          "List of subcomponent references";

        leaf name {
          type leafref {
            path "../config/name";
          }
          description
            "Reference to the subcomponent name";
        }

        container config {
          description
            "Configuration data ";

          uses inventory-subcomponent-ref-config;
        }

        container state {

          config false;

          description
            "Operational state data ";

          uses inventory-subcomponent-ref-config;
          uses inventory-subcomponent-ref-state;
        }
      }
    }
  }

  grouping inventory-component-config {
    description
      "Configuration data for components";

    leaf name {
      type string;
      description
        "Device name for the component -- this may not be a
        configurable parameter on many implementations";
    }
  }

  grouping inventory-component-state {
    description
      "Operational state data for device components.";

    leaf type {
      type union {
        type identityref {
          base oc-inv-types:openconfig-hardware-component;
        }
        type identityref {
          base oc-inv-types:openconfig-software-component;
        }
      }
      description
        "Type of component as identified by the system";
    }

    leaf id {
      type string;
      description
        "Unique identifier assigned by the system for the
        component";
    }

    leaf description {
      type string;
      description
        "System-supplied description of the component";
    }

    leaf serial_no {
      type string;
      description
        "System-assigned serial number of the component.";
    }

    leaf part_no {
      type string;
      description
        "System-assigned part number for the component.  This should
        be present in particular if the component is also an FRU
        (field replacable unit)";
    }
  }

  grouping inventory-component-top {
    description
      "Top-level grouping for components in the device inventory";

    container components {
      description
        "Enclosing container for the components in the system.";

      list component {
        key name;
        description
          "List of components, keyed by component name.";

        leaf name {
          type leafref {
            path "../config/name";
          }
          description
            "References the component name";
        }

        container config {
          description
            "Configuration data for each component";

          uses inventory-component-config;
        }

        container state {

          config false;

          description
            "Operational state data for each component";

          uses inventory-component-config;
          uses inventory-component-state;
        }

        uses inventory-component-properties-top;
        uses inventory-subcomponent-ref-top;
      }
    }
  }

  // data definition statements

  uses inventory-component-top;


  // augments

  augment "/ocif:interfaces/ocif:interface/ocif:state" {
    //TODO: add 'when' or other condition to make sure this
    //leafref points to a component of type PORT.
    description
      "Adds a reference from the base interface to the corresponding
      port in the device inventory.";

    leaf hardware-port {
      type leafref {
        path "/oc-inv:components/oc-inv:component/oc-inv:name";
      }
      description
        "References the hardware port in the device inventory";
    }
  }

}
